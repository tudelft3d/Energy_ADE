FME workspace Energy_ADE_3.0_to_extended_3DCityDB_4.x.fmw

Parameters:
- citydb_schema = citydb
- CityGML_file = $(FME_WORKSPACE_DIR)\input_citygml\Alderaan_Energy_ADE_All.gml
- Energy_ADE_xsd_file = $(FME_WORKSPACE_DIR)\xsd\Energy_ADE_3.0_beta7.xsd   # "" Energy_ADE_xsd_file
- Energy_ADE_3.0_version = 3.0 beta 7 (2025-10-14)   # ADE_version

Readers:
- CITYGML_2: CITYGML from $(CityGML_file) in EPSG:28992

Note: READ ME - Setup before running this workbench / Summary: / This workbench was created with FME Form 2024.2.4.0 and will import Energy ADE 3.0 data into the chosen 3DCityDB schema. / Default schema is the "citydb" one. Please be aware that any previously loaded Energy ADE 3.0 data will be deleted and replaced. "Normal" CityGML data will be left untouched, i.e. neither overwritten nor deleted. / Prerequisites: / 1) The Energy ADE 3.0 database schema is already installed / 2) "Normal" CityGML data (i.e. without Energy ADE contents) has already been imported into the database using the Importer/Exporter. / Workbench setup: / In the Navigation panel here on the left, check the User Parameters and the Database Connections entries and set: / 1) the input CityGML file name (best if you put the file in the subfolder ./citygml_input_file) / 2) the target database schema name (default it "citydb") / 3) the Energy ADE 3.0 xsd file (default is to the ./xsd subfolder; generally no need to change it) / 3) the database connection parameters. / The very first time you load this workbench, you will have to add the connection and edit the connection parameters. / a) Go to the menu Tools\FME Options, / b) Choose the "Database Connections" tab, / c) Right-click and import the connection stored in the ./db_connection/3dcitydb_connection_no_credentials.xml file. A connection named "Shared 3DCityDB connection" will be loaded and appear in the Navigator tab. / d) Open it and enter your connection parameters, test and save the connection. From now on, you will be able to connect to your 3DCityDB instance. / Running the workbench: / Simply run the workbench, however BEWARE: do not "Enable feature caching"! See menu Run (or open the Run icon). / Depending on the size of your input data, the workbench might stop with a generic error. It generally means that you have consumed all available memory for caching data. / Last update: 26 October 2025 / ---------------------------------------------------------------- / This workbench has been created by: / Dr. Giorgio Agugiaro / 3D Geoinformation group / Delft University of Technology / The Netherlands / https://3d.bk.tudelft.nl/gagugiaro/
Note: Start the process
Creator_2
    GEOMTYPE = Geometry Object
    NUM = 1
    CREATED -> AttributeCreator_57
Junction_17
    -> Junction_21
    -> Junction_24
    -> Junction_59
    -> Junction_16
Junction_16
    -> Junction_18
    -> Junction_14
Junction_14
    -> Junction_13
    -> Junction_15
Junction_13
    -> Junction_12
    -> Junction_11
Junction_11
    -> Junction_10
Junction_24
    -> Junction_25
    -> Junction_27
    -> Junction_26
    -> Junction_23
Junction_25
    -> Junction_28
    -> Junction_30
Junction_28
    -> Junction_22
    -> Junction_29
Junction_22
    -> Junction_32
    -> Junction_31
Junction_32
    -> Junction_38
    -> Junction_35
Note: Junction_35 : Output
Junction_41
    -> QualifiedAttributeWriter_2 [objectclass_name_list]
Junction_38
    -> Junction_33
    -> Junction_37
Junction_33
    -> Junction_94
    -> Junction_36
Note: Junction_36 : Output
Junction_43
    -> QualifiedAttributeWriter_3 [objectclass_name_list]
Note: Junction_36 : Output
Junction_45
    -> QualifiedAttributeWriter_5 [objectclass_name_list]
Junction_94
    -> Junction_117
    -> Junction_55
Note: QualifiedAttributeWriter_4 : objectclass_name_list
Junction_55
    -> Junction_56
Junction_47
    -> Junction_34
    -> Junction_46
    -> Junction_48
    -> Junction_51
    -> Junction_60
    -> Junction_177
    -> Junction_182
    -> Junction_184
    -> Junction_198
Junction_165
    -> Junction_154
Junction_163
    -> Junction_152
Junction_164
    -> Junction_153
ADE_Feature_editor_7
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_47 [REQUESTOR]
ADE_CityObject_editor
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> AttributeRenamer_104
Note: Rename Library attributes
AttributeRenamer_104
    ATTR_TABLE = RENAME_SET_DEFAULT type_codeSpace > type_codespace
    KEEP_RENAMED_ONLY = no
    MISSING_INPUT_ATTRS = REMOVE
    -> CreationDate-Converter_8 [Tester_5_Input]
CreationDate-Converter_8: CreationTerminationDate-Converter
    CREATION_DATE = @Value(creation_date)
    TERMINATION_DATE = @Value(termination_date)
    FeatureHolder_Output -> FeatureWriter [citydb.cityobject]
Note: Insert into CITYOBJECT
FeatureWriter
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> Junction_99
    citydb.cityobject -> FeatureWriter_2 [citydb.ng3_library]
Note: AttributeKeeper_23 : Input
Junction_99
    -> Junction_100
Note: Insert into ng3_LIBRARY
FeatureWriter_2
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_library -> AttributeKeeper_16
AttributeKeeper_16
    CREATE_BULK_MODE_FEATURES = NO
    KEEP_ATTRS = gmlid,id
    -> Junction_65
Note: AttributeRenamer_18 : Input
Junction_65
    -> Junction_66
Note: AttributeKeeper_16 : Output
Junction_66
    -> AttributeRenamer_18
AttributeRenamer_18
    ATTR_TABLE:
      RENAME_SET_DEFAULT id > library_id
      RENAME_SET_DEFAULT gmlid > gml_parent_id
    KEEP_RENAMED_ONLY = no
    MISSING_INPUT_ATTRS = REMOVE
    -> FeatureMerger_31 [SUPPLIER]
    -> FeatureMerger_32 [SUPPLIER]
ADE_Feature_editor_1
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_31 [REQUESTOR]
Note: Assign parent id
FeatureMerger_31
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_5
Note: Rename Gas attributes
AttributeManager_5
    ATTR_TABLE = RENAME_SET_VALUE library_code_codeSpace > library_code_codespace (buffer)
    USER_EXPOSED_ATTRIBUTES = nrg3_library_code,nrg3_library_code_codeSpace,nrg3_is_ventilated,nrg3_r_value,co_id
    -> AttributeCreator_21
Note: boolean to numeric
AttributeCreator_21
    ATTR_TABLE = SET_TO is_ventilated (logical) = FME_CONDITIONAL:DEFAULT_VALUE'0'BOOL_OP;OR;COMPOSITE_TEST;1;TEST @Value(is_ventilated) = true'1'FME_NUM_CONDITIONS2___
    -> FeatureWriter_4 [citydb.cityobject]
ADE_Feature_editor_2
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_32 [REQUESTOR]
FeatureMerger_32
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_6
Note: Rename SoliMaterial attributes
AttributeManager_6
    ATTR_TABLE:
      RENAME_SET_VALUE library_code_codeSpace > library_code_codespace (buffer)
      RENAME_SET_VALUE thermal_conductivity > thm_conductivity (real64)
      RENAME_SET_VALUE thermal_conductivity_uom > thm_conductivity_uom (buffer)
      RENAME_SET_VALUE specific_heat_capacity > spec_heat_capacity (real64)
      RENAME_SET_VALUE specific_heat_capacity_uom > spec_heat_capacity_uom (buffer)
    USER_EXPOSED_ATTRIBUTES = nrg3_is_ventilated,nrg3_library_code,co_id,co_parent_id
    -> FeatureWriter_4 [citydb.cityobject]
Note: Insert into CITYOBJECT
FeatureWriter_4
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_5 [citydb.ng3_material]
Note: Insert into ng3_MATERIAL
FeatureWriter_5
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_material -> AttributeKeeper_17
AttributeKeeper_17
    CREATE_BULK_MODE_FEATURES = NO
    KEEP_ATTRS = gmlid,id
    -> Junction_67
Note: AttributeRenamer_29 : Input
Junction_67
    -> Junction_68
Note: AttributeKeeper_17 : Output
Junction_68
    -> AttributeRenamer_29
AttributeRenamer_29
    ATTR_TABLE:
      RENAME_SET_DEFAULT id > material_id
      RENAME_SET_DEFAULT gmlid > gml_link
    KEEP_RENAMED_ONLY = no
    MISSING_INPUT_ATTRS = REMOVE
    -> FeatureMerger_41 [SUPPLIER]
ADE_CityObject_editor_2
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> AttributeRenamer_13
Note: Rename Library attributes
AttributeRenamer_13
    ATTR_TABLE = RENAME_SET_DEFAULT type_codeSpace > type_codespace
    KEEP_RENAMED_ONLY = no
    MISSING_INPUT_ATTRS = REMOVE
    -> FeatureWriter_80 [citydb.cityobject]
Note: Insert into CITYOBJECT
FeatureWriter_80
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_81 [citydb.ng3_library]
    citydb.cityobject -> Junction_58
Note: AttributeKeeper_23 : Input
Junction_58
    -> Junction_100
Note: Insert into ng3_LIBRARY
FeatureWriter_81
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_library -> AttributeKeeper_86
AttributeKeeper_86
    CREATE_BULK_MODE_FEATURES = NO
    KEEP_ATTRS = gmlid,id
    -> Junction_73
Note: AttributeRenamer_14 : Input
Junction_73
    -> Junction_74
Note: AttributeKeeper_86 : Output
Junction_74
    -> AttributeRenamer_14
AttributeRenamer_14
    ATTR_TABLE:
      RENAME_SET_DEFAULT id > library_id
      RENAME_SET_DEFAULT gmlid > gml_parent_id
    KEEP_RENAMED_ONLY = no
    MISSING_INPUT_ATTRS = REMOVE
    -> FeatureMerger_34 [SUPPLIER]
    -> FeatureMerger_38 [SUPPLIER]
ADE_Feature_editor_4
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_34 [REQUESTOR]
Note: Assign parent id
FeatureMerger_34
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_8
Note: Rename LayeredConstruction attributes
AttributeManager_8
    ATTR_TABLE = RENAME_SET_VALUE library_code_codeSpace > library_code_codespace (buffer)
    USER_EXPOSED_ATTRIBUTES = nrg3_is_ventilated,nrg3_library_code,thermal_conductivity_uom,specific_heat_capacity
    -> FeatureWriter_6 [citydb.cityobject]
Note: Insert into CITYOBJECT
FeatureWriter_6
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_7 [citydb.ng3_layered_construction]
    citydb.cityobject -> FeatureWriter_16 [citydb.ng3_layered_construction]
Note: Insert into ng3_LAYEREDCONSTRUCTION?old
FeatureWriter_7 [off]
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_layered_construction -> AttributeKeeper_19
FeatureWriter_16
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_layered_construction -> AttributeKeeper_19
    citydb.ng3_layered_construction -> Junction_20
AttributeKeeper_19
    CREATE_BULK_MODE_FEATURES = NO
    KEEP_ATTRS = gmlid,id
    -> Junction_63
    -> Junction_69
    -> Junction_71
Note: AttributeRenamer_25 : Input
Junction_71
    -> Junction_72
Note: AttributeKeeper_19 : Output
Junction_72
    -> AttributeRenamer_25
AttributeRenamer_25
    ATTR_TABLE:
      RENAME_SET_DEFAULT id > layered_construction_id
      RENAME_SET_DEFAULT gmlid > gml_link
    KEEP_RENAMED_ONLY = no
    MISSING_INPUT_ATTRS = REMOVE
    -> FeatureMerger_40 [SUPPLIER]
Note: AttributeRenamer_17 : Input
Junction_69
    -> Junction_70
Note: AttributeKeeper_19 : Output
Junction_70
    -> AttributeRenamer_17
AttributeRenamer_17
    ATTR_TABLE:
      RENAME_SET_DEFAULT gmlid > gml_parent_id
      RENAME_SET_DEFAULT id > layered_construction_id
    KEEP_RENAMED_ONLY = no
    MISSING_INPUT_ATTRS = REMOVE
    -> FeatureMerger_39 [SUPPLIER]
ADE_Feature_editor_5
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_38 [REQUESTOR]
Note: Assign parent id
FeatureMerger_38
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeRenamer_26
AttributeRenamer_26
    ATTR_TABLE = RENAME_SET_DEFAULT base_layered_construction_xlink_href > gml_link
    KEEP_RENAMED_ONLY = no
    MISSING_INPUT_ATTRS = REMOVE
    -> StringReplacer_11
Note: Trim # from XLinks
StringReplacer_11
    CASE = NO
    FIND_TEXT = #
    NO_MATCH = _FME_NO_OP_
    REGEXP = NO
    SRC_ATTRS = gml_link
    -> FeatureMerger_40 [REQUESTOR]
Note: Assign base_layered_construction id
FeatureMerger_40
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeManager_10
Note: Rename ReverseLayeredConstruction attributes
AttributeManager_10
    USER_EXPOSED_ATTRIBUTES = nrg3_is_ventilated,nrg3_library_code,thermal_conductivity_uom,specific_heat_capacity,co_parent_id,co_id,table_name
    -> FeatureWriter_9 [citydb.cityobject]
Note: Insert into CITYOBJECT
FeatureWriter_9
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_10 [citydb.ng3_layered_construction]
Note: Insert into ng3_LAYEREDCONSTRUCTION
FeatureWriter_10
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_layered_construction -> AttributeKeeper_51
AttributeKeeper_51
    CREATE_BULK_MODE_FEATURES = NO
    KEEP_ATTRS = gmlid,id
    -> Junction_63
Note: AttributeRenamer_85 : Input
Junction_63
    -> Junction_119
ADE_Feature_editor_3
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_39 [REQUESTOR]
Note: Assign parent id
FeatureMerger_39
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeRenamer_28
AttributeRenamer_28
    ATTR_TABLE = RENAME_SET_DEFAULT material_xlink_href > gml_link
    KEEP_RENAMED_ONLY = no
    MISSING_INPUT_ATTRS = REMOVE
    -> StringReplacer_12
Note: Trim # from XLinks
StringReplacer_12
    CASE = NO
    FIND_TEXT = #
    NO_MATCH = _FME_NO_OP_
    REGEXP = NO
    SRC_ATTRS = gml_link
    -> FeatureMerger_41 [REQUESTOR]
Note: Assign material_id
FeatureMerger_41
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeManager_12
Note: Rename Layer attributes
AttributeManager_12
    ATTR_TABLE = REMOVE gml_link (buffer)
    USER_EXPOSED_ATTRIBUTES = nrg3_is_ventilated,nrg3_library_code,thermal_conductivity_uom,specific_heat_capacity,co_id,table_name,co_parent_id
    -> FeatureWriter_11 [citydb.cityobject]
Note: Insert into CITYOBJECT
FeatureWriter_11
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_12 [citydb.ng3_layer]
Note: Insert into ng3_LAYER
FeatureWriter_12
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
ADE_CityObject_editor_3
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> AttributeRenamer_15
Note: Rename Library attributes
AttributeRenamer_15
    ATTR_TABLE = RENAME_SET_DEFAULT type_codeSpace > type_codespace
    KEEP_RENAMED_ONLY = no
    MISSING_INPUT_ATTRS = REMOVE
    -> FeatureWriter_83 [citydb.cityobject]
Note: Insert into CITYOBJECT
FeatureWriter_83
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_84 [citydb.ng3_library]
    citydb.cityobject -> Junction_101
Note: AttributeKeeper_89 : Input
Junction_101
    -> Junction_100
Note: Insert into ng3_LIBRARY
FeatureWriter_84
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_library -> AttributeKeeper_88
AttributeKeeper_88
    CREATE_BULK_MODE_FEATURES = NO
    KEEP_ATTRS = gmlid,id
    -> Junction_83
Note: AttributeRenamer_16 : Input
Junction_83
    -> Junction_84
Note: AttributeKeeper_88 : Output
Junction_84
    -> AttributeRenamer_16
AttributeRenamer_16
    ATTR_TABLE:
      RENAME_SET_DEFAULT gmlid > gml_parent_id
      RENAME_SET_DEFAULT id > library_id
    KEEP_RENAMED_ONLY = no
    MISSING_INPUT_ATTRS = REMOVE
    -> FeatureMerger_46 [SUPPLIER]
ADE_Feature_editor_6
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_46 [REQUESTOR]
Note: Assign parent id
FeatureMerger_46
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> FeatureMerger_43 [REQUESTOR]
Junction_49
    -> ADE_Feature_editor_8 [ADE_Feature]
ADE_Feature_editor_8
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> AttributeRemover_10
Note: Remove redundant gml time attributes
AttributeRemover_10
    LIST_ATTRS = temporal_extent_gml_time_period_gml_begin_gml_time_instant_gml_related_time{} temporal_extent_gml_time_period_gml_end_gml_time_instant_gml_related_time{} temporal_extent_gml_time_period_gml_related_time{}
    -> AttributeManager_14
Note: Rename TimeSeries attributes
AttributeManager_14
    ATTR_TABLE:
      RENAME_SET_VALUE acquisition_method_codeSpace > acquisition_method_codespace (buffer)
      RENAME_SET_VALUE temporal_extent_gml_time_period_gml_begin_position > period_begin (buffer)
      RENAME_SET_VALUE temporal_extent_gml_time_period_gml_end_position > period_end (buffer)
      RENAME_SET_VALUE uom_uom > uom (buffer)
      RENAME_SET_VALUE number_of_header_lines > num_of_header_lines (int64)
      RENAME_SET_VALUE auth_type (buffer)
      RENAME_SET_VALUE auth_type_codeSpace > auth_type_codespace (buffer)
      RENAME_SET_VALUE connection_type_codeSpace > connection_type_codespace (buffer)
    USER_EXPOSED_ATTRIBUTES = nrg3_is_ventilated,nrg3_library_code,thermal_conductivity_uom,specific_heat_capacity,co_parent_id,co_id,table_name
    -> AttributeCreator_25
Note: Insert into CITYOBJECT
FeatureWriter_13
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_14 [citydb.ng3_time_series]
Note: Insert into ng3_TIME_SERIES
FeatureWriter_14
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_time_series -> AttributeKeeper_90
AttributeKeeper_90
    CREATE_BULK_MODE_FEATURES = NO
    KEEP_ATTRS = gml_parent_id,id
    -> Junction_75
    -> Junction_79
    -> Junction_77
Note: Junction_76 : Input
Junction_77
    -> Junction_81
Note: AttributeKeeper_90 : Output
Junction_81
    -> AttributeRenamer_36
AttributeRenamer_36
    ATTR_TABLE:
      RENAME_SET_DEFAULT gml_parent_id > gmlid
      RENAME_SET_DEFAULT id > time_series_id
    KEEP_RENAMED_ONLY = no
    MISSING_INPUT_ATTRS = REMOVE
    -> FeatureMerger_43 [SUPPLIER]
Note: Assign time_series_id
FeatureMerger_43
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> AttributeManager_16
    UNMERGED_REQUESTOR -> AttributeManager_16
Note: Rename Schedule attributes
AttributeManager_16
    ATTR_TABLE:
      RENAME_SET_VALUE library_code_codeSpace > library_code_codespace (buffer)
      RENAME_SET_VALUE type_codeSpace > type_codespace (buffer)
      RENAME_SET_VALUE temporal_extent > time_interval (real64)
      RENAME_SET_VALUE temporal_extent_unit > time_interval_unit (buffer)
      RENAME_SET_VALUE temporal_extent_radix > time_interval_radix (uint64)
      RENAME_SET_VALUE temporal_extent_factor > time_interval_factor (int64)
      REMOVE time_series_xlink_href (buffer)
      REMOVE schedule_component{}.xlink_href (buffer)
    USER_EXPOSED_ATTRIBUTES = nrg3_is_ventilated,nrg3_library_code,thermal_conductivity_uom,specific_heat_capacity,co_parent_id,co_id,table_name
    -> FeatureWriter_15 [citydb.cityobject]
Note: Insert into CITYOBJECT
FeatureWriter_15
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_3 [citydb.ng3_schedule00]
Note: Insert into ng3_SCHEDULE
FeatureWriter_3
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_schedule00 -> AttributeKeeper_26
AttributeKeeper_26
    CREATE_BULK_MODE_FEATURES = NO
    KEEP_ATTRS = gmlid,id
    -> AttributeRenamer_38
    -> Junction_76
    -> Junction_88
    -> Junction_40
    -> Junction_91
    -> Junction_93
Note: AttributeRenamer_37 : Input
Junction_76
    -> Junction_82
Note: AttributeKeeper_26 : Output
Junction_82
    -> AttributeRenamer_37
AttributeRenamer_37
    ATTR_TABLE:
      RENAME_SET_DEFAULT gmlid > gml_link
      RENAME_SET_DEFAULT id > schedule_id
    KEEP_RENAMED_ONLY = no
    MISSING_INPUT_ATTRS = REMOVE
    -> FeatureMerger_48 [SUPPLIER]
Note: AttributeRenamer_63 : Input
Junction_88
    -> Junction_89
Note: AttributeKeeper_26 : Output
Junction_89
    -> AttributeRenamer_63
AttributeRenamer_63
    ATTR_TABLE:
      RENAME_SET_DEFAULT gmlid > gml_link
      RENAME_SET_DEFAULT id > schedule_id
    KEEP_RENAMED_ONLY = no
    MISSING_INPUT_ATTRS = REMOVE
    -> FeatureMerger_60 [SUPPLIER]
Note: AttributeRenamer_122 : Input
Junction_40
    -> Junction_90
Note: AttributeKeeper_26 : Output
Junction_90
    -> AttributeRenamer_122
AttributeRenamer_122
    ATTR_TABLE = RENAME_SET_DEFAULT gmlid > gml_link
    KEEP_RENAMED_ONLY = no
    MISSING_INPUT_ATTRS = REMOVE
    -> AttributeRenamer_123
    -> AttributeRenamer_124
    -> AttributeRenamer_125
AttributeRenamer_125
    ATTR_TABLE = RENAME_SET_DEFAULT id > ventilation_schedule_id
    KEEP_RENAMED_ONLY = no
    MISSING_INPUT_ATTRS = REMOVE
    -> FeatureMerger_94 [SUPPLIER]
AttributeRenamer_123
    ATTR_TABLE = RENAME_SET_DEFAULT id > heating_schedule_id
    KEEP_RENAMED_ONLY = no
    MISSING_INPUT_ATTRS = REMOVE
    -> FeatureMerger_92 [SUPPLIER]
AttributeRenamer_124
    ATTR_TABLE = RENAME_SET_DEFAULT id > cooling_schedule_id
    KEEP_RENAMED_ONLY = no
    MISSING_INPUT_ATTRS = REMOVE
    -> FeatureMerger_93 [SUPPLIER]
Note: AttributeRenamer_2 : Input
Junction_91
    -> Junction_92
Note: AttributeKeeper_26 : Output
Junction_92
    -> AttributeRenamer_2
AttributeRenamer_2
    ATTR_TABLE:
      RENAME_SET_DEFAULT gmlid > gml_link
      RENAME_SET_DEFAULT id > schedule_id
    KEEP_RENAMED_ONLY = no
    MISSING_INPUT_ATTRS = REMOVE
    -> FeatureMerger_99 [SUPPLIER]
Note: SuitabilityWriter : Schedule
Junction_93
    -> Junction_95
Note: Junction_94 : Input
Junction_95
    -> Junction_96
AttributeRenamer_38
    ATTR_TABLE:
      RENAME_SET_DEFAULT gmlid > gml_parent_id
      RENAME_SET_DEFAULT id > parent_schedule_id
    KEEP_RENAMED_ONLY = no
    MISSING_INPUT_ATTRS = REMOVE
    -> FeatureMerger_47 [SUPPLIER]
Note: Assign parent id
FeatureMerger_47
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeRenamer_39
AttributeRenamer_39
    ATTR_TABLE = RENAME_SET_DEFAULT schedule_component_member_xlink_href > gml_link
    KEEP_RENAMED_ONLY = no
    MISSING_INPUT_ATTRS = REMOVE
    -> StringReplacer_16
Note: Trim # from XLinks
StringReplacer_16
    CASE = NO
    FIND_TEXT = #
    NO_MATCH = _FME_NO_OP_
    REGEXP = NO
    SRC_ATTRS = gml_link
    -> FeatureMerger_48 [REQUESTOR]
Note: Assign target Schedule_id
FeatureMerger_48
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeManager_18
Note: Rename ScheduleComponent attributes
AttributeManager_18
    ATTR_TABLE:
      RENAME_SET_VALUE type_codeSpace > type_codespace (buffer)
      REMOVE gml_link (buffer)
    USER_EXPOSED_ATTRIBUTES = nrg3_is_ventilated,nrg3_library_code,thermal_conductivity_uom,specific_heat_capacity
    -> FeatureWriter_17 [citydb.cityobject]
Note: Insert into CITYOBJECT
FeatureWriter_17
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_18 [citydb.ng3_schedule_component]
Note: Insert into ng3_SCHEDULE_COMPONENT
FeatureWriter_18
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Note: AttributeRenamer_36 : Input
Junction_75
    -> Junction_78
Note: AttributeKeeper_90 : Output
Junction_78
    -> AttributeRenamer_46
AttributeRenamer_46
    ATTR_TABLE:
      RENAME_SET_DEFAULT gml_parent_id > gmlid
      RENAME_SET_DEFAULT id > time_series_id
    KEEP_RENAMED_ONLY = no
    MISSING_INPUT_ATTRS = REMOVE
    -> FeatureMerger_52 [SUPPLIER]
Note: AttributeRenamer_75 : Input
Junction_79
    -> Junction_80
Note: AttributeKeeper_24 : Output
Junction_80
    -> AttributeRenamer_75
AttributeRenamer_75
    ATTR_TABLE:
      RENAME_SET_DEFAULT gml_parent_id > gmlid
      RENAME_SET_DEFAULT id > time_series_id
    KEEP_RENAMED_ONLY = no
    MISSING_INPUT_ATTRS = REMOVE
    -> FeatureMerger_69 [SUPPLIER]
ADE_Feature_editor_9
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_51 [REQUESTOR]
ADE_CityObject_editor_4
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> CreationDate-Converter_5 [Tester_5_Input]
CreationDate-Converter_5: CreationTerminationDate-Converter
    CREATION_DATE = @Value(creation_date)
    TERMINATION_DATE = @Value(termination_date)
    FeatureHolder_Output -> FeatureWriter_19 [citydb.cityobject]
Note: Insert into CITYOBJECT
FeatureWriter_19
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> Junction_102
Note: AttributeKeeper_27 : Input
Junction_102
    -> Junction_100
ADE_Feature_editor_10
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_57 [REQUESTOR]
Junction_181
    -> ADE_CityObject_editor_5 [ADE_CityObject]
ADE_CityObject_editor_5
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_54 [REQUESTOR]
Junction_185
    -> ADE_CityObject_editor_6 [ADE_CityObject]
ADE_CityObject_editor_6
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_62 [REQUESTOR]
Junction_186
    -> ADE_CityObject_editor_7 [ADE_CityObject]
ADE_CityObject_editor_7
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_64 [REQUESTOR]
ADE_CityObject_editor_8
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_66 [REQUESTOR]
    ADE_CityObject -> GeometryRemover_21
GeometryRemover_21
    REMOVE_COORDSYS = No
    -> AttributeKeeper_41
AttributeKeeper_41
    CREATE_BULK_MODE_FEATURES = NO
    KEEP_ATTRS = gmlid,id
    -> AttributeRenamer_70
AttributeRenamer_70
    ATTR_TABLE:
      RENAME_SET_DEFAULT gmlid > gml_parent_id
      RENAME_SET_DEFAULT id > co_parent_id
    KEEP_RENAMED_ONLY = no
    MISSING_INPUT_ATTRS = REMOVE
    -> FeatureMerger_66 [SUPPLIER]
Note: Assign parent_id
FeatureMerger_66
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_35
    UNMERGED_REQUESTOR -> AttributeCreator_29
Note: Non top-level Urban Function Areas
AttributeCreator_29
    ATTR_TABLE = SET_TO co_parent_id (varchar(14)) = FME_NULL_VALUE
    -> AttributeManager_35
Note: Rename ArbanFunctionArea attributes
AttributeManager_35
    ATTR_TABLE:
      RENAME_SET_VALUE citygml_class > class (buffer)
      RENAME_SET_VALUE citygml_class_codeSpace > class_codespace (buffer)
      RENAME_SET_VALUE type_codeSpace > type_codespace (buffer)
      RENAME_SET_VALUE code_codeSpace > code_codespace (buffer)
    USER_EXPOSED_ATTRIBUTES = co_id,table_name
    -> ListConcatenator
ListConcatenator
    DROP_EMPTY_PARTS = Yes
    LIST_ATTR = citygml_function{}
    SEP = --/\--
    VAL_ATTR = function
    -> ListConcatenator_2
ListConcatenator_2
    DROP_EMPTY_PARTS = Yes
    LIST_ATTR = citygml_function{}.codeSpace
    SEP = --/\--
    VAL_ATTR = function_codespace
    -> ListConcatenator_3
ListConcatenator_3
    DROP_EMPTY_PARTS = Yes
    LIST_ATTR = citygml_usage{}
    SEP = --/\--
    VAL_ATTR = usage
    -> ListConcatenator_4
ListConcatenator_4
    DROP_EMPTY_PARTS = Yes
    LIST_ATTR = citygml_usage{}.codeSpace
    SEP = --/\--
    VAL_ATTR = usage_codespace
    -> NullAttributeMapper
NullAttributeMapper
    ATTRCHOICE_ACTION = ALL
    NULL_TREATMENT_LU = DELETEATTR
    SOURCE_ATTR_VAL_LU = SETNULL EMPTY MISSINGATTR
    ATTRCHOICE = All Attributes
    NULL_TREATMENT = Missing
    SOURCE_ATTR_VAL = Null Empty "Missing (Selected Attributes Only)"
    -> FeatureWriter_38 [citydb.cityobject]
Note: Insert into CITYOBJECT
FeatureWriter_38
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_22
    citydb.cityobject -> AttributeKeeper_83
GeometryRemover_22
    REMOVE_COORDSYS = No
    -> FeatureMerger_88 [REQUESTOR]
AttributeKeeper_83
    CREATE_BULK_MODE_FEATURES = NO
    KEEP_ATTRS = id
    -> Deaggregator_5
    -> GeometryRemover_23
Deaggregator_5
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> AttributeFilter_14
AttributeFilter_14
    ATTR_NAME = _geometry_name
    ATTR_VALUES = <Empty>,<Missing>,<Null>,<Unfiltered>,referencePoint,geometry
    referencePoint -> FeatureMerger_88 [SUPPLIER]
    geometry -> SurfaceGeometryWriter_6
FeatureMerger_88
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_26
    MERGED -> Junction_104
    UNMERGED_REQUESTOR -> GeometryRemover_26
    UNMERGED_REQUESTOR -> Junction_104
Note: AttributeKeeper_35 : Input
Junction_104
    -> Junction_100
GeometryRemover_26
    REMOVE_COORDSYS = No
    -> FeatureMerger_119 [REQUESTOR]
Note: Assign surface_geometry_id
FeatureMerger_119
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_39 [citydb.cityobjectgroup]
    UNMERGED_REQUESTOR -> FeatureWriter_39 [citydb.cityobjectgroup]
Note: Insert into CITYOBJECTGROUP
FeatureWriter_39
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobjectgroup -> FeatureWriter_41 [citydb.ng3_urban_function_area]
    citydb.cityobjectgroup -> AttributeFilter_9
    SUMMARY -> Junction_158
Note: Insert into ng3_UTILITY_FUNCTION_AREA
FeatureWriter_41
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Junction_187
    -> ADE_Feature_editor_11 [ADE_Feature]
ADE_Feature_editor_11
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_68 [REQUESTOR]
ADE_Feature_editor_12
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_70 [REQUESTOR]
ADE_Feature_editor_13
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_72 [REQUESTOR]
ADE_Feature_editor_14
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_74 [REQUESTOR]
Junction_188
    -> AttributeFilter_18
AttributeFilter_18
    ATTR_NAME = citygml_feature_role
    ATTR_VALUES = <Empty>,<Missing>,<Null>,<Unfiltered>,boundedBy,thermalBoundary
    boundedBy -> ADE_CityObject_editor_10 [ADE_CityObject]
    thermalBoundary -> ADE_CityObject_editor_15 [ADE_CityObject]
ADE_CityObject_editor_10
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_105 [REQUESTOR]
ADE_CityObject_editor_9
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_89 [REQUESTOR]
ADE_CityObject_editor_11
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_86 [REQUESTOR]
ADE_CityObject_editor_12
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_87 [REQUESTOR]
ADE_Feature_editor
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_TARGET_URI = @Value(citygml_target_uri)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_Feature -> FeatureMerger_90 [REQUESTOR]
Feature_editor_2 [off]
    GMLID = @Value(gmlid)
    GML_PARENT_ID = @Value(gml_parent_id)
    ID = @Value(id)
    OBJECTCLASS_ID = @Value(objectclass_id)
    OBJECTCLASS_NAME = @Value(objectclass_name)
Feature_editor
    GMLID = @Value(gmlid)
    GML_PARENT_ID = @Value(gml_parent_id)
    ID = @Value(id)
    OBJECTCLASS_ID = @Value(objectclass_id)
    OBJECTCLASS_NAME = @Value(objectclass_name)
    Feature -> AttributeKeeper_82
AttributeKeeper_82
    CREATE_BULK_MODE_FEATURES = NO
    KEEP_ATTRS = id
    KEEP_LIST = citygml_target{}
    -> ListExploder_17
ListExploder_17
    ATTR_ACCUM_MODE = Merge List Attributes
    ATTR_CONFLICT_RES_LOOKUP = INCOMING_IF_CONFLICT
    LIST_ATTR = citygml_target{}
    ATTR_CONFLICT_RES = Use List Attribute Values
    ELEMENTS -> AttributeRenamer_150
AttributeRenamer_150
    ATTR_TABLE:
      RENAME_SET_DEFAULT citygml_target > gml_link
      RENAME_SET_DEFAULT id > surface_data_id
    KEEP_RENAMED_ONLY = no
    MISSING_INPUT_ATTRS = REMOVE
    -> StringReplacer_60
Note: Trim # from XLinks
StringReplacer_60
    CASE = NO
    FIND_TEXT = #
    NO_MATCH = _FME_NO_OP_
    REGEXP = NO
    SRC_ATTRS = gml_link
    -> Junction_157
Junction_157
    -> Junction_9
Feature_editor_3
    GMLID = @Value(gmlid)
    GML_PARENT_ID = @Value(gml_parent_id)
    ID = @Value(id)
    OBJECTCLASS_ID = @Value(objectclass_id)
    OBJECTCLASS_NAME = @Value(objectclass_name)
    Feature -> GeometryRemover_13
GeometryRemover_13
    REMOVE_COORDSYS = No
    -> AttributeKeeper_2
AttributeKeeper_2
    CREATE_BULK_MODE_FEATURES = NO
    KEEP_ATTRS = gmlid,id
    -> AttributeRenamer_6
AttributeRenamer_6
    ATTR_TABLE = RENAME_SET_DEFAULT id > address_id
    KEEP_RENAMED_ONLY = no
    MISSING_INPUT_ATTRS = REMOVE
    -> Junction_155
Junction_155
    -> Junction_156
Junction_191
    -> CityObject_editor_12 [CityObject]
CityObject_editor_12
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_178
CityObject_editor_13
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_179
Note: Please note: / Bridge, Tunnel and WaterBody modules are currently missing from this workbench. However, they can be added and treated in a similar way as other CityObjects
CityObject_editor_14
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_180
Junction_180
    -> Junction_179
Junction_179
    -> Junction_178
Junction_178
    -> Junction_116
CityObject_editor_3
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_120
    CityObject_without_parent -> Junction_120
Junction_120
    -> Junction_166
    -> Junction_116
CityObject_editor_4
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_121
Junction_121
    -> Junction_116
    -> Junction_166
Note: AttributeKeeper_3 : Output
Junction_111
    -> AttributeRenamer_4
Note: From Buildings/Parts
AttributeRenamer_4
    ATTR_TABLE:
      RENAME_SET_DEFAULT gmlid > gml_parent_id
      RENAME_SET_DEFAULT id > building_id
    KEEP_RENAMED_ONLY = no
    MISSING_INPUT_ATTRS = REMOVE
    -> FeatureMerger_89 [SUPPLIER]
Note: Assign parent_id
Note: Only for debugging purpose!!!!!!!!
FeatureMerger_89
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeCreator_44
    UNMERGED_REQUESTOR -> AttributeCreator_17
Note: boolean to numeric
AttributeCreator_44
    ATTR_TABLE = SET_TO is_cooled (logical) = FME_CONDITIONAL:DEFAULT_VALUE'0'BOOL_OP;OR;COMPOSITE_TEST;1;TEST @Value(is_cooled) = true'1'FME_NUM_CONDITIONS2___
    -> AttributeCreator_45
Note: boolean to numeric
AttributeCreator_45
    ATTR_TABLE = SET_TO is_heated (logical) = FME_CONDITIONAL:DEFAULT_VALUE'0'BOOL_OP;OR;COMPOSITE_TEST;1;TEST @Value(is_heated) = true'1'FME_NUM_CONDITIONS2___
    -> AttributeCreator_46
Note: boolean to numeric
AttributeCreator_46
    ATTR_TABLE = SET_TO coincides_with_lod2_hull (logical) = FME_CONDITIONAL:DEFAULT_VALUE'0'BOOL_OP;OR;COMPOSITE_TEST;1;TEST @Value(coincides_with_lod2_hull) = true'1'FME_NUM_CONDITIONS2___
    -> AttributeCreator_47
Note: boolean to numeric
AttributeCreator_47
    ATTR_TABLE = SET_TO coincides_with_lod3_hull (logical) = FME_CONDITIONAL:DEFAULT_VALUE'0'BOOL_OP;OR;COMPOSITE_TEST;1;TEST @Value(coincides_with_lod3_hull) = true'1'FME_NUM_CONDITIONS2___
    -> FeatureWriter_79 [citydb.cityobject]
Note: Insert into CITYOBJECT
FeatureWriter_79
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_20
    citydb.cityobject -> AttributeKeeper_56
GeometryRemover_20
    REMOVE_COORDSYS = No
    -> FeatureMerger_114 [REQUESTOR]
AttributeKeeper_56
    CREATE_BULK_MODE_FEATURES = NO
    KEEP_ATTRS = id
    -> Deaggregator
    -> GeometryRemover_19
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> AttributeFilter_21
AttributeFilter_21
    ATTR_NAME = _geometry_name
    ATTR_VALUES = <Empty>,<Missing>,<Null>,<Unfiltered>,referencePoint,lod1Solid,lod2Solid,lod3Solid
    referencePoint -> FeatureMerger_114 [SUPPLIER]
    lod1Solid -> SurfaceGeometryWriter
    lod2Solid -> SurfaceGeometryWriter_2
    lod3Solid -> SurfaceGeometryWriter_3
FeatureMerger_114
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_25
    MERGED -> Junction_105
    UNMERGED_REQUESTOR -> GeometryRemover_25
    UNMERGED_REQUESTOR -> Junction_105
Note: AttributeKeeper_18 : Input
Junction_105
    -> Junction_100
GeometryRemover_25
    REMOVE_COORDSYS = No
    -> FeatureMerger_110 [REQUESTOR]
Note: Assign surface_geometry_id
FeatureMerger_110
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_57 [citydb.ng3_building_partition]
    UNMERGED_REQUESTOR -> FeatureWriter_57 [citydb.ng3_building_partition]
Note: Insert into ng3_BUILDING_PARTITION
FeatureWriter_57
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_building_partition -> AttributeKeeper_55
    citydb.ng3_building_partition -> AttributeCreator_5
    SUMMARY -> Junction_158
AttributeCreator_5
    ATTR_TABLE = SET_TO height{0} (varchar(200))
    -> QualifiedAttributeWriter_2 [CityObject]
QualifiedAttributeWriter_2
    ID = @Value(id)
    OBJECTCLASS_ID = @Value(objectclass_id)
    OBJECTCLASS_NAME = @Value(objectclass_name)
    TABLE_NAME = @Value(table_name)
    TABLE_NAME_2 = @Value(table_name)
    cp_citydb_schema = $(citydb_schema)
AttributeKeeper_55
    CREATE_BULK_MODE_FEATURES = NO
    KEEP_ATTRS = gmlid,id
    KEEP_LIST = usage_zone{}.xlink_href
    -> AttributeKeeper_68
    -> Junction_61
Note: AttributeRenamer_110 : Input
Junction_61
    -> Junction_62
Note: AttributeKeeper_55 : Output
Junction_62
    -> AttributeRenamer_110
Note: From ThermalZone
AttributeRenamer_110
    ATTR_TABLE:
      RENAME_SET_DEFAULT gmlid > gml_parent_id
      RENAME_SET_DEFAULT id > thermal_zone_id
    KEEP_RENAMED_ONLY = no
    MISSING_INPUT_ATTRS = REMOVE
    -> FeatureMerger_84 [SUPPLIER]
AttributeKeeper_68
    CREATE_BULK_MODE_FEATURES = NO
    KEEP_ATTRS = id
    KEEP_LIST = usage_zone{}.xlink_href
    -> Junction_97
Note: ListExploder_14 : Input
Junction_97
    -> Junction_98
Note: AttributeKeeper_68 : Output
Junction_98
    -> ListExploder_14
ListExploder_14
    ATTR_ACCUM_MODE = Merge List Attributes
    ATTR_CONFLICT_RES_LOOKUP = INCOMING_IF_CONFLICT
    LIST_ATTR = usage_zone{}
    ATTR_CONFLICT_RES = Use List Attribute Values
    ELEMENTS -> StringReplacer_46
StringReplacer_46
    CASE = NO
    FIND_TEXT = #
    NO_MATCH = _FME_NO_OP_
    REGEXP = NO
    SRC_ATTRS = xlink_href
    -> AttributeRenamer_129
AttributeRenamer_129
    ATTR_TABLE:
      RENAME_SET_DEFAULT id > thermal_zone_id
      RENAME_SET_DEFAULT xlink_href > gmlid
    KEEP_RENAMED_ONLY = no
    MISSING_INPUT_ATTRS = REMOVE
    -> FeatureMerger_96 [SUPPLIER]
Note: AttributeKeeper_3 : Output
Junction_113
    -> AttributeRenamer_112
Note: From Buildings/Parts
AttributeRenamer_112
    ATTR_TABLE:
      RENAME_SET_DEFAULT gmlid > gml_parent_id
      RENAME_SET_DEFAULT id > building_id
    KEEP_RENAMED_ONLY = no
    MISSING_INPUT_ATTRS = REMOVE
    -> FeatureMerger_86 [SUPPLIER]
    -> FeatureMerger_87 [SUPPLIER]
Note: Assign parent_id
Note: Only for debugging purpose!!!!!!!!
FeatureMerger_86
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> FeatureMerger_96 [REQUESTOR]
    UNMERGED_REQUESTOR -> AttributeCreator_40
Note: Assign thermal_zone_id
FeatureMerger_96
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> AttributeRenamer_108
    UNMERGED_REQUESTOR -> AttributeRenamer_108
AttributeRenamer_108
    ATTR_TABLE = RENAME_SET_DEFAULT heating_schedule_xlink_href > gml_link
    KEEP_RENAMED_ONLY = no
    MISSING_INPUT_ATTRS = REMOVE
    -> StringReplacer_43
Note: Trim # from XLinks
StringReplacer_43
    CASE = NO
    FIND_TEXT = #
    NO_MATCH = _FME_NO_OP_
    REGEXP = NO
    SRC_ATTRS = gml_link
    -> FeatureMerger_92 [REQUESTOR]
Note: Assign schedule_id for heating
FeatureMerger_92
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeRenamer_120
    UNMERGED_REQUESTOR -> AttributeRenamer_120
AttributeRenamer_120
    ATTR_TABLE = RENAME_SET_DEFAULT cooling_schedule_xlink_href > gml_link
    KEEP_RENAMED_ONLY = no
    MISSING_INPUT_ATTRS = REMOVE
    -> StringReplacer_44
Note: Trim # from XLinks
StringReplacer_44
    CASE = NO
    FIND_TEXT = #
    NO_MATCH = _FME_NO_OP_
    REGEXP = NO
    SRC_ATTRS = gml_link
    -> FeatureMerger_93 [REQUESTOR]
Note: Assign schedule_id for cooling
FeatureMerger_93
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeRenamer_121
    UNMERGED_REQUESTOR -> AttributeRenamer_121
AttributeRenamer_121
    ATTR_TABLE = RENAME_SET_DEFAULT ventilation_schedule_xlink_href > gml_link
    KEEP_RENAMED_ONLY = no
    MISSING_INPUT_ATTRS = REMOVE
    -> StringReplacer_45
Note: Trim # from XLinks
StringReplacer_45
    CASE = NO
    FIND_TEXT = #
    NO_MATCH = _FME_NO_OP_
    REGEXP = NO
    SRC_ATTRS = gml_link
    -> FeatureMerger_94 [REQUESTOR]
Note: Assign schedule_id for ventilation
FeatureMerger_94
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> BulkAttributeRenamer_71
    UNMERGED_REQUESTOR -> BulkAttributeRenamer_71
Note: UsageZone bulk renamer
BulkAttributeRenamer_71
    ATTRCHOICE_ACTION = NONPROTECTEDFME
    CASE_DISP = NO
    MODE_CHOICE = RENAME
    PATTERN_ACTION_DISP = STRINGREPLACE
    REPLACE_PATTERN = internal_heat_gains
    REPLACE_STR = int_heat_gains
    ATTRCHOICE = All Attributes
    -> BulkAttributeRenamer_72
BulkAttributeRenamer_72
    ATTRCHOICE_ACTION = NONPROTECTEDFME
    CASE_DISP = NO
    MODE_CHOICE = RENAME
    PATTERN_ACTION_DISP = STRINGREPLACE
    REPLACE_PATTERN = convective_fraction
    REPLACE_STR = conv
    ATTRCHOICE = All Attributes
    -> BulkAttributeRenamer_73
BulkAttributeRenamer_73
    ATTRCHOICE_ACTION = NONPROTECTEDFME
    CASE_DISP = NO
    MODE_CHOICE = RENAME
    PATTERN_ACTION_DISP = STRINGREPLACE
    REPLACE_PATTERN = latent_fraction
    REPLACE_STR = lat
    ATTRCHOICE = All Attributes
    -> BulkAttributeRenamer_74
BulkAttributeRenamer_74
    ATTRCHOICE_ACTION = NONPROTECTEDFME
    CASE_DISP = NO
    MODE_CHOICE = RENAME
    PATTERN_ACTION_DISP = STRINGREPLACE
    REPLACE_PATTERN = radiant_fraction
    REPLACE_STR = rad
    ATTRCHOICE = All Attributes
    -> AttributeRenamer_119
Note: Rename UsageZone attributes
AttributeRenamer_119
    ATTR_TABLE = RENAME_SET_DEFAULT number_of_building_uom > num_of_building_units
    KEEP_RENAMED_ONLY = no
    MISSING_INPUT_ATTRS = REMOVE
    -> AttributeCreator_50
Note: boolean to numeric
AttributeCreator_50
    ATTR_TABLE = SET_TO is_primary (logical) = FME_CONDITIONAL:DEFAULT_VALUE'0'BOOL_OP;OR;COMPOSITE_TEST;1;TEST @Value(is_primary) = true'1'FME_NUM_CONDITIONS2___
    -> FeatureWriter_60 [citydb.cityobject]
Note: Insert into CITYOBJECT
FeatureWriter_60
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_14
    citydb.cityobject -> AttributeKeeper_58
GeometryRemover_14
    REMOVE_COORDSYS = No
    -> FeatureMerger_126 [REQUESTOR]
AttributeKeeper_58
    CREATE_BULK_MODE_FEATURES = NO
    KEEP_ATTRS = id
    -> Deaggregator_6
    -> GeometryRemover_31
Deaggregator_6
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeFilter_15
AttributeFilter_15
    ATTR_NAME = _geometry_name
    ATTR_VALUES = <Empty>,<Missing>,<Null>,<Unfiltered>,referencePoint,lod1Solid,lod2Solid,lod3Solid
    referencePoint -> FeatureMerger_126 [SUPPLIER]
    lod1Solid -> SurfaceGeometryWriter_9
    lod2Solid -> SurfaceGeometryWriter_11
    lod3Solid -> SurfaceGeometryWriter_12
FeatureMerger_126
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_9
    MERGED -> Junction_108
    UNMERGED_REQUESTOR -> GeometryRemover_9
    UNMERGED_REQUESTOR -> Junction_108
Note: AttributeKeeper_3 : Input
Junction_108
    -> Junction_100
GeometryRemover_9
    REMOVE_COORDSYS = No
    -> FeatureMerger_95 [REQUESTOR]
Note: Assign surface_geometry_id
FeatureMerger_95
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_71 [citydb.ng3_building_partition]
    UNMERGED_REQUESTOR -> FeatureWriter_71 [citydb.ng3_building_partition]
Note: Insert into ng3_BUILDING_PARTITION
FeatureWriter_71
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_building_partition -> AttributeCreator_6
    citydb.ng3_building_partition -> AttributeKeeper_65
    SUMMARY -> Junction_158
AttributeCreator_6
    ATTR_TABLE = SET_TO height{0} (varchar(200))
    -> QualifiedAttributeWriter_3 [CityObject]
QualifiedAttributeWriter_3
    ID = @Value(id)
    OBJECTCLASS_ID = @Value(objectclass_id)
    OBJECTCLASS_NAME = @Value(objectclass_name)
    TABLE_NAME = @Value(table_name)
    TABLE_NAME_2 = @Value(table_name)
    cp_citydb_schema = $(citydb_schema)
AttributeKeeper_65
    CREATE_BULK_MODE_FEATURES = NO
    KEEP_ATTRS = gmlid,id
    KEEP_LIST = building_unit{}
    -> AttributeKeeper_67
    -> AttributeKeeper_11
AttributeKeeper_11
    CREATE_BULK_MODE_FEATURES = NO
    KEEP_ATTRS = gmlid,id
    -> Junction_144
Note: Junction_143 : Input
Junction_144
    -> Junction_143
Note: AttributeKeeper_73 : Output
Junction_143
    -> AttributeRenamer_131
AttributeKeeper_67
    CREATE_BULK_MODE_FEATURES = NO
    KEEP_ATTRS = id
    KEEP_LIST = building_unit{}.xlink_href
    -> Junction_140
Note: ListExploder_13 : Input
Junction_140
    -> Junction_141
Note: AttributeKeeper_67 : Output
Junction_141
    -> ListExploder_13
ListExploder_13
    ATTR_ACCUM_MODE = Merge List Attributes
    ATTR_CONFLICT_RES_LOOKUP = INCOMING_IF_CONFLICT
    LIST_ATTR = building_unit{}
    ATTR_CONFLICT_RES = Use List Attribute Values
    ELEMENTS -> StringReplacer_48
StringReplacer_48
    CASE = NO
    FIND_TEXT = #
    NO_MATCH = _FME_NO_OP_
    REGEXP = NO
    SRC_ATTRS = xlink_href
    -> AttributeRenamer_127
AttributeRenamer_127
    ATTR_TABLE:
      RENAME_SET_DEFAULT id > usage_zone_id
      RENAME_SET_DEFAULT xlink_href > gmlid
    KEEP_RENAMED_ONLY = no
    MISSING_INPUT_ATTRS = REMOVE
    -> FeatureMerger_97 [SUPPLIER]
Note: Assign parent_id
Note: Only for debugging purpose!!!!!!!!
FeatureMerger_87
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> FeatureMerger_97 [REQUESTOR]
    UNMERGED_REQUESTOR -> AttributeCreator_41
Note: Assign usage_zone_id
FeatureMerger_97
    ATTR_ACCUM_MODE = Merge Supplier
    ATTR_CONFLICT_RES_LOOKUP = REQUESTOR_IF_CONFLICT
    IGNORE_NULLS = No
    JOIN_KEYS = @Value(gmlid) gmlid AUTO
    MERGE_TYPE = Attributes Only
    PROCESS_DUPS = NO
    REJECT_NULL_MISSING_KEYS = No
    SUPPLIERS_FIRST = No
    ATTR_CONFLICT_RES = Use Requestor
    MERGED -> AttributeRenamer_128
    UNMERGED_REQUESTOR -> AttributeRenamer_128
Note: Rename BuildingUnit attributes
AttributeRenamer_128
    ATTR_TABLE:
      RENAME_SET_DEFAULT number_of_rooms > num_of_rooms
      RENAME_SET_DEFAULT ownership_type_codeSpace > ownership_type_codespace
    KEEP_RENAMED_ONLY = no
    MISSING_INPUT_ATTRS = REMOVE
    -> FeatureWriter_72 [citydb.cityobject]
Note: Insert into CITYOBJECT
FeatureWriter_72
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_11
    citydb.cityobject -> AttributeKeeper_69
GeometryRemover_11
    REMOVE_COORDSYS = No
    -> FeatureMerger_130 [REQUESTOR]
AttributeKeeper_69
    CREATE_BULK_MODE_FEATURES = NO
    KEEP_ATTRS = id
    -> Deaggregator_7
    -> GeometryRemover_10
Deaggregator_7
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeFilter_16
AttributeFilter_16
    ATTR_NAME = _geometry_name
    ATTR_VALUES = <Empty>,<Missing>,<Null>,<Unfiltered>,referencePoint,lod1Solid,lod2Solid,lod3Solid
    referencePoint -> FeatureMerger_130 [SUPPLIER]
    lod1Solid -> SurfaceGeometryWriter_13
    lod2Solid -> SurfaceGeometryWriter_14
    lod3Solid -> SurfaceGeometryWriter_15
FeatureMerger_130
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_32
    MERGED -> Junction_109
    UNMERGED_REQUESTOR -> GeometryRemover_32
    UNMERGED_REQUESTOR -> Junction_109
Note: AttributeKeeper_76 : Input
Junction_109
    -> Junction_100
GeometryRemover_32
    REMOVE_COORDSYS = No
    -> FeatureMerger_98 [REQUESTOR]
Note: Assign surface_geometry_id
FeatureMerger_98
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_74 [citydb.ng3_building_partition]
    UNMERGED_REQUESTOR -> FeatureWriter_74 [citydb.ng3_building_partition]
Note: Insert into ng3_BUILDING_PARTITION
FeatureWriter_74
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_building_partition -> AttributeCreator_51
    citydb.ng3_building_partition -> AttributeKeeper_71
    SUMMARY -> Junction_158
AttributeCreator_51
    ATTR_TABLE = SET_TO height{0} (varchar(200))
    -> QualifiedAttributeWriter_5 [CityObject]
QualifiedAttributeWriter_5
    ID = @Value(id)
    OBJECTCLASS_ID = @Value(objectclass_id)
    OBJECTCLASS_NAME = @Value(objectclass_name)
    TABLE_NAME = @Value(table_name)
    TABLE_NAME_2 = @Value(table_name)
    cp_citydb_schema = $(citydb_schema)
AttributeKeeper_71
    CREATE_BULK_MODE_FEATURES = NO
    KEEP_ATTRS = gmlid,id,objectclass_name
    KEEP_LIST = address{}.xlink_href
    -> AttributeKeeper_72
    -> AttributeKeeper_74
    -> AttributeKeeper_73
AttributeKeeper_74
    CREATE_BULK_MODE_FEATURES = NO
    KEEP_ATTRS = objectclass_name,gmlid,id
    -> Junction_133
Note: AttributeFilter_4 : Input
Junction_133
    -> Junction_145
Note: AttributeKeeper_74 : Output
Junction_145
    -> AttributeFilter_4
AttributeKeeper_73
    CREATE_BULK_MODE_FEATURES = NO
    KEEP_ATTRS = gmlid,id
    -> Junction_142
Note: AttributeRenamer_131 : Input
Junction_142
    -> Junction_146
Note: Junction_142 : Output
Junction_146
    -> AttributeRenamer_131
AttributeRenamer_131
    ATTR_TABLE:
      RENAME_SET_DEFAULT id > building_partition_id
      RENAME_SET_DEFAULT gmlid > gml_parent_id
    KEEP_RENAMED_ONLY = no
    MISSING_INPUT_ATTRS = REMOVE
    -> FeatureMerger_90 [SUPPLIER]
Note: Assign parent_id
Note: Only for debugging purpose!!!!!!!!
FeatureMerger_90
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeRenamer_133
    UNMERGED_REQUESTOR -> AttributeCreator_7
AttributeRenamer_133
    ATTR_TABLE = RENAME_SET_DEFAULT occupancy_rate_xlink_href > gml_link
    KEEP_RENAMED_ONLY = no
    MISSING_INPUT_ATTRS = REMOVE
    -> StringReplacer_47
Note: Trim # from XLinks
StringReplacer_47
    CASE = NO
    FIND_TEXT = #
    NO_MATCH = _FME_NO_OP_
    REGEXP = NO
    SRC_ATTRS = gml_link
    -> FeatureMerger_99 [REQUESTOR]
Note: Assign schedule_id for heating
FeatureMerger_99
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> BulkAttributeRenamer
    UNMERGED_REQUESTOR -> BulkAttributeRenamer
Note: Bulk rename Occupants attributes
BulkAttributeRenamer
    ATTRCHOICE_ACTION = NONPROTECTEDFME
    CASE_DISP = YES
    MODE_CHOICE = RENAME
    PATTERN_ACTION_DISP = STRINGREPLACE
    REPLACE_PATTERN = heat_dissipation
    REPLACE_STR = heat_diss
    ATTRCHOICE = All Attributes
    -> BulkAttributeRenamer_79
BulkAttributeRenamer_79
    ATTRCHOICE_ACTION = NONPROTECTEDFME
    CASE_DISP = NO
    MODE_CHOICE = RENAME
    PATTERN_ACTION_DISP = STRINGREPLACE
    REPLACE_PATTERN = convective_fraction
    REPLACE_STR = conv
    ATTRCHOICE = All Attributes
    -> BulkAttributeRenamer_80
BulkAttributeRenamer_80
    ATTRCHOICE_ACTION = NONPROTECTEDFME
    CASE_DISP = NO
    MODE_CHOICE = RENAME
    PATTERN_ACTION_DISP = STRINGREPLACE
    REPLACE_PATTERN = latent_fraction
    REPLACE_STR = lat
    ATTRCHOICE = All Attributes
    -> BulkAttributeRenamer_81
BulkAttributeRenamer_81
    ATTRCHOICE_ACTION = NONPROTECTEDFME
    CASE_DISP = NO
    MODE_CHOICE = RENAME
    PATTERN_ACTION_DISP = STRINGREPLACE
    REPLACE_PATTERN = radiant_fraction
    REPLACE_STR = rad
    ATTRCHOICE = All Attributes
    -> BulkAttributeRenamer_78
BulkAttributeRenamer_78
    ATTRCHOICE_ACTION = NONPROTECTEDFME
    CASE_DISP = NO
    MODE_CHOICE = RENAME
    PATTERN_ACTION_DISP = STRINGREPLACE
    REPLACE_PATTERN = average
    REPLACE_STR = avg
    ATTRCHOICE = All Attributes
    -> AttributeRenamer_134
Note: Rename Occupants attributes
AttributeRenamer_134
    ATTR_TABLE:
      RENAME_SET_DEFAULT type_codeSpace > type_codespace
      RENAME_SET_DEFAULT number_of_occupants > num_of_occupants
      RENAME_SET_DEFAULT avg_diet_type_codeSpace > avg_diet_type_codespace
      RENAME_SET_DEFAULT avg_income_level_codeSpace > avg_income_level_codespace
      RENAME_SET_DEFAULT avg_instruction_level > avg_instr_level
      RENAME_SET_DEFAULT avg_instruction_level_codeSpace > avg_instr_level_codespace
    KEEP_RENAMED_ONLY = no
    MISSING_INPUT_ATTRS = REMOVE
    -> FeatureWriter_75 [citydb.cityobject]
Note: Insert into CITYOBJECT
FeatureWriter_75
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_76 [citydb.ng3_occupants]
Note: Insert into ng3_OCCUPANTS
FeatureWriter_76
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Note: AttributeKeeper_3 : Output
Junction_115
    -> AttributeRenamer_74
Note: From Buildings/Parts
AttributeRenamer_74
    ATTR_TABLE:
      RENAME_SET_DEFAULT gmlid > gml_parent_id
      RENAME_SET_DEFAULT id > building_id
    KEEP_RENAMED_ONLY = no
    MISSING_INPUT_ATTRS = REMOVE
    -> FeatureMerger_105 [SUPPLIER]
Note: Assign parent_id
Note: Only for debugging purpose!!!!!!!!
FeatureMerger_105
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> Junction_137
    UNMERGED_REQUESTOR -> AttributeCreator_18
Junction_137
    -> Junction_139
Note: AttributeKeeper_54 : Output
Junction_148
    -> AttributeFilter_4
AttributeFilter_4
    ATTR_NAME = objectclass_name
    ATTR_VALUES = <Empty>,<Missing>,<Null>,<Unfiltered>,Building,BuildingPart,BuildingUnit
    Building -> AttributeRenamer_90
    BuildingPart -> AttributeRenamer_90
    BuildingUnit -> AttributeRenamer_91
AttributeRenamer_90
    ATTR_TABLE = RENAME_SET_DEFAULT id > building_id
    KEEP_RENAMED_ONLY = no
    MISSING_INPUT_ATTRS = REMOVE
    -> AttributeRenamer_11
AttributeRenamer_91
    ATTR_TABLE = RENAME_SET_DEFAULT id > building_partition_id
    KEEP_RENAMED_ONLY = no
    MISSING_INPUT_ATTRS = REMOVE
    -> AttributeRenamer_11
Note: Building/Part or BuildingUnit
AttributeRenamer_11
    ATTR_TABLE = RENAME_SET_DEFAULT gmlid > gml_parent_id
    KEEP_RENAMED_ONLY = no
    MISSING_INPUT_ATTRS = REMOVE
    -> AttributeKeeper_18
AttributeKeeper_18
    CREATE_BULK_MODE_FEATURES = NO
    KEEP_ATTRS = building_id,building_partition_id,gml_parent_id
    -> FeatureMerger_72 [SUPPLIER]
    -> FeatureMerger_74 [SUPPLIER]
Note: Assign parent_id
FeatureMerger_72
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_41
Note: Rename RefurbishmentMeasure attributes
AttributeManager_41
    ATTR_TABLE:
      RENAME_SET_VALUE library_code_codeSpace > library_code_codespace (buffer)
      RENAME_SET_VALUE type_codeSpace > type_codespace (buffer)
    USER_EXPOSED_ATTRIBUTES = nrg3_is_ventilated,nrg3_library_code,thermal_conductivity_uom,specific_heat_capacity,co_parent_id,type,network_type_codeSpace,co_id,table_name
    -> AttributeCreator_33
Note: Insert into CITYOBJECT
FeatureWriter_48
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_50 [citydb.ng3_refurbishment_measure]
Note: Insert into ng3_REFURBISHMENT_MEASURE
FeatureWriter_50
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
Note: Assign parent_id
FeatureMerger_74
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_43
Note: Rename EnergyPerformanceCertificate attributes
AttributeManager_43
    ATTR_TABLE:
      RENAME_SET_VALUE type_codeSpace > type_codespace (buffer)
      RENAME_SET_VALUE certification_method > cert_method (buffer)
      RENAME_SET_VALUE certification_uri > cert_uri (buffer)
    USER_EXPOSED_ATTRIBUTES = nrg3_is_ventilated,nrg3_library_code,thermal_conductivity_uom,specific_heat_capacity,co_parent_id,type,network_type_codeSpace,co_id,table_name
    -> AttributeCreator_52
Note: Insert into CITYOBJECT
FeatureWriter_49
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_51 [citydb.ng3_energy_perf_cert]
Note: Insert into ng3_ENERGY_PERF_CERT
FeatureWriter_51
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
Junction_189
    -> AttributeFilter_11
AttributeFilter_11
    ATTR_NAME = citygml_feature_role
    ATTR_VALUES = <Empty>,<Missing>,<Null>,<Unfiltered>,boundedBy,thermalBoundary
    boundedBy -> CityObject_editor_5 [CityObject]
    boundedBy -> GeometryRemover_12
    thermalBoundary -> Junction_53
    thermalBoundary -> GeometryRemover_12
    thermalBoundary -> FeatureMerger_12_UnmergedRequestor
Note: These are new ThematicSurfaces from the ADE / Some are children of ThermalZones, other of Buildings (PartyWalls)
FeatureMerger_12_UnmergedRequestor: Inspector [off]
Note: FeatureHolder_6 : Input
Junction_53
    -> Junction_54
ADE_CityObject_editor_15
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_84 [REQUESTOR]
Note: Assign parent_id
Note: Only for debugging purpose!!!!!!!!
FeatureMerger_84
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> Junction_138
    UNMERGED_REQUESTOR -> AttributeCreator_26
Junction_138
    -> Junction_139
Junction_139
    -> BulkAttributeRenamer_64
Note: Bulk rename for ThematicSurfaces
BulkAttributeRenamer_64
    ATTRCHOICE_ACTION = NONPROTECTEDFME
    CASE_DISP = NO
    MODE_CHOICE = RENAME
    PATTERN_ACTION_DISP = STRINGREPLACE
    REPLACE_PATTERN = bdg_bdry_surf_
    ATTRCHOICE = All Attributes
    -> ListExploder_12
ListExploder_12
    ATTR_ACCUM_MODE = Merge List Attributes
    ATTR_CONFLICT_RES_LOOKUP = INCOMING_IF_CONFLICT
    LIST_ATTR = is_adiabatic{}
    ATTR_CONFLICT_RES = Use List Attribute Values
    ELEMENTS -> AttributeRenamer_115
    <REJECTED> -> AttributeRenamer_115
Note: Rename ADE _ThematicSurface attributes
AttributeRenamer_115
    ATTR_TABLE:
      RENAME_SET_DEFAULT azimuth{0} > azimuth
      RENAME_SET_DEFAULT azimuth{0}.units > azimuth_uom
      RENAME_SET_DEFAULT ground_view_factor{0} > ground_view_factor
      RENAME_SET_DEFAULT ground_view_factor{0}.units > ground_view_factor_uom
      RENAME_SET_DEFAULT heat_capacity{0} > heat_capacity
      RENAME_SET_DEFAULT heat_capacity{0}.units > heat_capacity_uom
      RENAME_SET_DEFAULT inclination{0} > inclination
      RENAME_SET_DEFAULT inclination{0}.units > inclination_uom
      RENAME_SET_DEFAULT opaque_surface_area{0} > opaque_surf_area
      RENAME_SET_DEFAULT opaque_surface_area{0}.units > opaque_surf_area_uom
      RENAME_SET_DEFAULT opening_to_surface_ratio{0} > open_to_surf_ratio
      RENAME_SET_DEFAULT opening_to_surface_ratio{0}.units > open_to_surf_ratio_uom
      RENAME_SET_DEFAULT sky_view_factor{0} > sky_view_factor
      RENAME_SET_DEFAULT sky_view_factor{0}.units > sky_view_factor_uom
      RENAME_SET_DEFAULT thickness{0} > thickness
      RENAME_SET_DEFAULT thickness{0}.units > thickness_uom
      RENAME_SET_DEFAULT total_surface_area{0} > total_surf_area
      RENAME_SET_DEFAULT total_surface_area{0}.units > total_surf_area_uom
    KEEP_RENAMED_ONLY = no
    MISSING_INPUT_ATTRS = REMOVE
    -> AttributeCreator_43
Note: boolean to numeric
AttributeCreator_43
    ATTR_TABLE = SET_TO is_adiabatic (logical) = FME_CONDITIONAL:DEFAULT_VALUE'0'BOOL_OP;OR;COMPOSITE_TEST;1;TEST @Value(is_adiabatic) = true'1'FME_NUM_CONDITIONS2___
    -> FeatureWriter_59 [citydb.cityobject]
Note: Insert into CITYOBJECT
FeatureWriter_59
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_28
    citydb.cityobject -> AttributeKeeper_40
GeometryRemover_28
    REMOVE_COORDSYS = No
    -> FeatureMerger_83 [REQUESTOR]
AttributeKeeper_40
    CREATE_BULK_MODE_FEATURES = NO
    KEEP_ATTRS = id
    -> Deaggregator_2
    -> AttributeKeeper_84
Deaggregator_2
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeFilter_6
AttributeFilter_6
    ATTR_NAME = _geometry_name
    ATTR_VALUES = <Empty>,<Missing>,<Null>,<Unfiltered>,referencePoint,lod2MultiSurface,lod3MultiSurface
    referencePoint -> FeatureMerger_83 [SUPPLIER]
    lod2MultiSurface -> SurfaceGeometryWriter_4
    lod3MultiSurface -> SurfaceGeometryWriter_5
FeatureMerger_83
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover
    MERGED -> Junction_106
    UNMERGED_REQUESTOR -> GeometryRemover
    UNMERGED_REQUESTOR -> Junction_106
Note: AttributeKeeper_18 : Input
Junction_106
    -> Junction_100
GeometryRemover
    REMOVE_COORDSYS = No
    -> FeatureMerger_117 [REQUESTOR]
Note: Assign surface_geometry_id
FeatureMerger_117
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_64 [citydb.thematic_surface]
    UNMERGED_REQUESTOR -> FeatureWriter_64 [citydb.thematic_surface]
Note: Insert into THEMATIC_SURFACE
FeatureWriter_64
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.thematic_surface -> FeatureWriter_62 [citydb.ng3_thematic_surface]
    SUMMARY -> Junction_158
Note: Insert into ng3_THEMATIC_SURFACE
FeatureWriter_62
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_thematic_surface -> AttributeKeeper_60
    citydb.ng3_thematic_surface -> TestFilter
TestFilter
    DEFAULT_VALUE = <UNFILTERED>
    PASSED_TEST_GROUP_OUTPUT = FIRST
    TEST_LIST = "BOOL_OP,OR,COMPOSITE_TEST,""""""1"""""",TEST_CLAUSE,TEST thermal_zone_id ATTRIBUTE_HAS_A_VALUE """,thermal_zone_id ATTRIBUTE_HAS_A_VALUE
    thermal_zone_id ATTRIBUTE_HAS_A_VALUE -> AttributeKeeper_61
AttributeKeeper_60
    CREATE_BULK_MODE_FEATURES = NO
    KEEP_ATTRS = id,gmlid
    -> Junction_128
Note: AttributeRenamer_116 : Input
Junction_128
    -> Junction_129
Note: AttributeKeeper_60 : Output
Junction_129
    -> AttributeRenamer_116
AttributeRenamer_116
    ATTR_TABLE:
      RENAME_SET_DEFAULT gmlid > gml_parent_id
      RENAME_SET_DEFAULT id > thematic_surface_id
    KEEP_RENAMED_ONLY = no
    MISSING_INPUT_ATTRS = REMOVE
    -> FeatureMerger_85 [SUPPLIER]
CityObject_editor_5
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_122
Junction_122
    -> Junction_116
    -> GeometryRemover_4
GeometryRemover_12
    REMOVE_COORDSYS = No
    -> AttributeKeeper_8
AttributeKeeper_8
    CREATE_BULK_MODE_FEATURES = NO
    KEEP_ATTRS = citygml_feature_role,gml_id
    -> AttributeRenamer
AttributeRenamer
    ATTR_TABLE:
      RENAME_SET_DEFAULT gml_id > gml_parent_id
      RENAME_SET_DEFAULT citygml_feature_role > parent_citygml_feature_role
    KEEP_RENAMED_ONLY = no
    MISSING_INPUT_ATTRS = REMOVE
    -> FeatureMerger [SUPPLIER]
Junction_190
    -> FeatureMerger [REQUESTOR]
FeatureMerger
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeFilter_12
AttributeFilter_12
    ATTR_NAME = parent_citygml_feature_role
    ATTR_VALUES = <Empty>,<Missing>,<Null>,<Unfiltered>,boundedBy,thermalBoundary
    boundedBy -> CityObject_editor_6 [CityObject]
    thermalBoundary -> AttributeRemover
AttributeRemover
    REMOVE_ATTRS = parent_citygml_feature_role
    -> Junction_50
    -> FeatureMerger_12_UnmergedRequestor_2
Note: These are new Openings from the ADE / Used for ThermalBoundaries
FeatureMerger_12_UnmergedRequestor_2: Inspector [off]
Note: FeatureHolder_22 : Input
Junction_50
    -> Junction_52
ADE_CityObject_editor_13
    CITYGML_CREATIONDATE = @Value(citygml_creationDate)
    CITYGML_FEATURE_ROLE = @Value(citygml_feature_role)
    CITYGML_FEATURE_ROLE_ATTR_NAME = @Value(citygml_feature_role_attr_name)
    CITYGML_FEATURE_ROLE_ATTR_VAL = @Value(citygml_feature_role_attr_val)
    CITYGML_RELATIVE_TO_TERRAIN = @Value(citygml_relative_to_terrain)
    CITYGML_RELATIVE_TO_WATER = @Value(citygml_relative_to_water)
    CITYGML_TARGET_URI = @Value(citygml_target_uri)
    CITYGML_TERMINATIONDATE = @Value(citygml_terminationDate)
    GML_DESCRIPTION = @Value(gml_description)
    GML_ID = @Value(gml_id)
    GML_NAME = @Value(gml_name)
    GML_PARENT_ID = @Value(gml_parent_id)
    OBJECTCLASS_ID = @Value(objectclass_id)
    OBJECTCLASS_NAME = @Value(objectclass_name)
    ADE_CityObject -> FeatureMerger_85 [REQUESTOR]
Note: Assign parent_id
FeatureMerger_85
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> BulkAttributeRenamer_68
Note: Bulk rename for Openings
BulkAttributeRenamer_68
    ATTRCHOICE_ACTION = NONPROTECTEDFME
    CASE_DISP = NO
    MODE_CHOICE = RENAME
    PATTERN_ACTION_DISP = STRINGREPLACE
    REPLACE_PATTERN = bdg_opn_
    ATTRCHOICE = All Attributes
    -> AttributeRenamer_117
Note: Rename ADE _Openings
AttributeRenamer_117
    ATTR_TABLE:
      RENAME_SET_DEFAULT area{0} > area
      RENAME_SET_DEFAULT area{0}.units > area_uom
      RENAME_SET_DEFAULT azimuth{0} > azimuth
      RENAME_SET_DEFAULT azimuth{0}.units > azimuth_uom
      RENAME_SET_DEFAULT inclination{0} > inclination
      RENAME_SET_DEFAULT inclination{0}.units > inclination_uom
      RENAME_SET_DEFAULT ground_view_factor{0} > ground_view_factor
      RENAME_SET_DEFAULT ground_view_factor{0}.units > ground_view_factor_uom
      RENAME_SET_DEFAULT sky_view_factor{0} > sky_view_factor
      RENAME_SET_DEFAULT sky_view_factor{0}.units > sky_view_factor_uom
    KEEP_RENAMED_ONLY = no
    MISSING_INPUT_ATTRS = REMOVE
    -> FeatureWriter_66 [citydb.cityobject]
Note: Insert into CITYOBJECT
FeatureWriter_66
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_15
    citydb.cityobject -> AttributeKeeper_59
GeometryRemover_15
    REMOVE_COORDSYS = No
    -> FeatureMerger_123 [REQUESTOR]
AttributeKeeper_59
    CREATE_BULK_MODE_FEATURES = NO
    KEEP_ATTRS = id
    -> Deaggregator_4
    -> AttributeKeeper_63
Deaggregator_4
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeFilter_8
AttributeFilter_8
    ATTR_NAME = _geometry_name
    ATTR_VALUES = <Empty>,<Missing>,<Null>,<Unfiltered>,referencePoint,lod3MultiSurface
    referencePoint -> FeatureMerger_123 [SUPPLIER]
    lod3MultiSurface -> SurfaceGeometryWriter_10
FeatureMerger_123
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_8
    MERGED -> Junction_107
    UNMERGED_REQUESTOR -> GeometryRemover_8
    UNMERGED_REQUESTOR -> Junction_107
Note: AttributeKeeper_5 : Input
Junction_107
    -> Junction_100
GeometryRemover_8
    REMOVE_COORDSYS = No
    -> FeatureMerger_91 [REQUESTOR]
Note: Assign surface_geometry_id
FeatureMerger_91
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_68 [citydb.opening]
    UNMERGED_REQUESTOR -> FeatureWriter_68 [citydb.opening]
Note: Insert into OPENING
FeatureWriter_68
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.opening -> FeatureWriter_65 [citydb.ng3_opening]
    citydb.opening -> AttributeKeeper_64
    SUMMARY -> Junction_158
Note: Insert into ng3_OPENING
FeatureWriter_65
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
CityObject_editor_6
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_123
Junction_123
    -> GeometryRemover_5
    -> Junction_116
CityObject_editor_2
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_64
    CityObject_without_parent -> Junction_64
Junction_64
    -> Junction_116
CityObject_editor_7
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_124
    CityObject_without_parent -> Junction_124
Junction_124
    -> Junction_116
CityObject_editor_15
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_183
    CityObject_without_parent -> Junction_183
Junction_183
    -> Junction_116
CityObject_editor_10
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_126
    CityObject_without_parent -> Junction_126
CityObject_editor_11
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_127
CityObject_editor_16
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_194
CityObject_editor_17
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_195
CityObject_editor_18
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_196
Junction_196
    -> Junction_195
Junction_195
    -> Junction_194
Junction_194
    -> Junction_127
Junction_127
    -> Junction_126
Junction_126
    -> Junction_116
CityObject_editor_19
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_197
    CityObject_without_parent -> Junction_197
Junction_197
    -> Junction_116
CityObject_editor_8
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_125
    CityObject_without_parent -> Junction_125
CityObject_editor_9
    GMLID = @Value(gmlid)
    GML_ID = @Value(gml_id)
    GML_PARENT_ID = @Value(gml_parent_id)
    ID = @Value(id)
    OBJECTCLASS_ID = @Value(objectclass_id)
    OBJECTCLASS_NAME = @Value(objectclass_name)
    CityObject -> Junction_176
    CityObject_without_parent -> Junction_176
Junction_176
    -> Junction_125
Junction_125
    -> Junction_116
Note: AttributeKeeper_10 : Output
Junction_135
    -> AttributeRenamer_8
Note: All Cityobjects
AttributeRenamer_8
    ATTR_TABLE:
      RENAME_SET_DEFAULT gmlid > gml_parent_id
      RENAME_SET_DEFAULT coid > cityobject_id
    KEEP_RENAMED_ONLY = no
    MISSING_INPUT_ATTRS = REMOVE
    -> FeatureMerger_70 [SUPPLIER]
Note: Assign parent_id
FeatureMerger_70
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_39
Note: Rename UtilityNetworkConnectionce attributes
AttributeManager_39
    ATTR_TABLE:
      RENAME_SET_VALUE network_type_codeSpace > network_type_codespace (buffer)
      RENAME_SET_VALUE function_in_network_codeSpace > function_in_network_codespace (buffer)
      RENAME_SET_VALUE usage_in_network_codeSpace > usage_in_network_codespace (buffer)
    USER_EXPOSED_ATTRIBUTES = nrg3_is_ventilated,nrg3_library_code,thermal_conductivity_uom,specific_heat_capacity,co_parent_id,type,network_type_codeSpace
    -> FeatureWriter_46 [citydb.cityobject]
Note: Insert into CITYOBJECT
FeatureWriter_46
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_47 [citydb.ng3_utl_ntw_connection]
Note: Insert into ng3_UTL_NTW_CONNECTION
FeatureWriter_47
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Note: AttributeKeeper_10 : Output
Junction_136
    -> AttributeRenamer_76
Note: All CityObjects
AttributeRenamer_76
    ATTR_TABLE:
      RENAME_SET_DEFAULT gmlid > gml_parent_id
      RENAME_SET_DEFAULT id > cityobject_id
    KEEP_RENAMED_ONLY = no
    MISSING_INPUT_ATTRS = REMOVE
    -> FeatureMerger_68 [SUPPLIER]
Note: Assign parent_id
FeatureMerger_68
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> FeatureMerger_69 [REQUESTOR]
Note: Assign time_series_id
FeatureMerger_69
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> AttributeManager_37
    UNMERGED_REQUESTOR -> AttributeManager_37
Note: Rename Resource attributes
AttributeManager_37
    ATTR_TABLE:
      RENAME_SET_VALUE type_codeSpace > type_codespace (buffer)
      RENAME_SET_VALUE operation_type_codeSpace > operation_type_codespace (buffer)
      RENAME_SET_VALUE amount_type_codeSpace > amount_type_codespace (buffer)
      RENAME_SET_VALUE normalization_parameter > normalization_param (buffer)
      RENAME_SET_VALUE end_use > enduse (buffer)
      RENAME_SET_VALUE end_use_codeSpace > enduse_codespace (buffer)
      RENAME_SET_VALUE energy_carrier_codeSpace > energy_carrier_codespace (buffer)
      RENAME_SET_VALUE source_codeSpace > source_codespace (buffer)
    USER_EXPOSED_ATTRIBUTES = nrg3_is_ventilated,nrg3_library_code,thermal_conductivity_uom,specific_heat_capacity,co_parent_id
    -> AttributeCreator_30
Note: boolean to numeric
AttributeCreator_30
    ATTR_TABLE = SET_TO is_amount_normalized (logical) = FME_CONDITIONAL:DEFAULT_VALUE'0'BOOL_OP;OR;COMPOSITE_TEST;1;TEST @Value(is_amount_normalized) = true'1'FME_NUM_CONDITIONS2___
    -> AttributeCreator_31
Note: boolean to numeric
AttributeCreator_31
    ATTR_TABLE = SET_TO is_dangerous (logical) = FME_CONDITIONAL:DEFAULT_VALUE'0'BOOL_OP;OR;COMPOSITE_TEST;1;TEST @Value(is_dangerous) = true'1'FME_NUM_CONDITIONS2___
    -> AttributeCreator_32
Note: boolean to numeric
AttributeCreator_32
    ATTR_TABLE = SET_TO is_recyclable (logical) = FME_CONDITIONAL:DEFAULT_VALUE'0'BOOL_OP;OR;COMPOSITE_TEST;1;TEST @Value(is_recyclable) = true'1'FME_NUM_CONDITIONS2___
    -> FeatureWriter_43 [citydb.cityobject]
Note: Insert into CITYOBJECT
FeatureWriter_43
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_44 [citydb.ng3_resource]
Note: Insert into ng3_RESOURCE
FeatureWriter_44
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Note: AttributeKeeper_14 : Output
Junction_131
    -> AttributeRenamer_44
Note: All CityObjects
AttributeRenamer_44
    ATTR_TABLE:
      RENAME_SET_DEFAULT gmlid > gml_parent_id
      RENAME_SET_DEFAULT id > cityobject_id
    KEEP_RENAMED_ONLY = no
    MISSING_INPUT_ATTRS = REMOVE
    -> FeatureMerger_51 [SUPPLIER]
Note: Assign parent_id
FeatureMerger_51
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> FeatureMerger_52 [REQUESTOR]
Note: Assign time_series_id
FeatureMerger_52
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> AttributeManager_22
Note: Rename WeatherData attributes
AttributeManager_22
    ATTR_TABLE = RENAME_SET_VALUE value_type_codeSpace > value_type_codespace (buffer)
    USER_EXPOSED_ATTRIBUTES = nrg3_is_ventilated,nrg3_library_code,thermal_conductivity_uom,specific_heat_capacity,co_parent_id
    -> FeatureWriter_21 [citydb.cityobject]
Note: Insert into CITYOBJECT
FeatureWriter_21
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_22 [citydb.ng3_weather_data]
Note: Insert into ng3_WEATHER_DATA
FeatureWriter_22
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
Note: AttributeKeeper_10 : Output
Junction_151
    -> AttributeRenamer_48
Note: All CityObjects
AttributeRenamer_48
    ATTR_TABLE:
      RENAME_SET_DEFAULT gmlid > gml_parent_id
      RENAME_SET_DEFAULT id > cityobject_id
    KEEP_RENAMED_ONLY = no
    MISSING_INPUT_ATTRS = REMOVE
    -> FeatureMerger_54 [SUPPLIER]
    -> FeatureMerger_62 [SUPPLIER]
    -> FeatureMerger_64 [SUPPLIER]
Note: Assign parent_id
Note: Only for debugging purpose!!!!!!!!
Note: Only for debugging purpose!!!!!!!!
FeatureMerger_54
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_25
    UNMERGED_REQUESTOR -> AttributeCreator_37
Note: Rename Device attributes
AttributeManager_25
    ATTR_TABLE:
      RENAME_SET_VALUE type_codeSpace > type_codespace (buffer)
      RENAME_SET_VALUE number_of_devices > num_of_devices (int64)
      RENAME_SET_VALUE heat_dissipation > heat_diss (real64)
      RENAME_SET_VALUE heat_dissipation_uom > heat_diss_uom (buffer)
      RENAME_SET_VALUE heat_dissipation_convective_fraction > heat_diss_conv (real64)
      RENAME_SET_VALUE heat_dissipation_convective_fraction_uom > heat_diss_conv_uom (buffer)
      RENAME_SET_VALUE heat_dissipation_latent_fraction > heat_diss_lat (real64)
      RENAME_SET_VALUE heat_dissipation_latent_fraction_uom > heat_diss_lat_uom (buffer)
      RENAME_SET_VALUE heat_dissipation_radiant_fraction > heat_diss_rad (real64)
      RENAME_SET_VALUE heat_dissipation_radiant_fraction_uom > heat_diss_rad_uom (buffer)
      RENAME_SET_VALUE heat_source_codeSpace > heat_source_codespace (buffer)
      RENAME_SET_VALUE cop_source_temperature > cop_source_temp (real64)
      RENAME_SET_VALUE cop_source_temperature_uom > cop_source_temp_uom (buffer)
      RENAME_SET_VALUE cop_operation_temperature > cop_operation_temp (real64)
      RENAME_SET_VALUE cop_operation_temperature_uom > cop_operation_temp_uom (buffer)
      RENAME_SET_VALUE maximum_cover_ratio > max_cover_ratio (real64)
      RENAME_SET_VALUE maximum_cover_ratio_uom > max_cover_ratio_uom (buffer)
    USER_EXPOSED_ATTRIBUTES = table_name
    -> AttributeCreator_28
Note: boolean to numeric
AttributeCreator_28
    ATTR_TABLE = SET_TO has_condensation (logical) = FME_CONDITIONAL:DEFAULT_VALUE'0'BOOL_OP;OR;COMPOSITE_TEST;1;TEST @Value(has_condensation) = true'1'FME_NUM_CONDITIONS2___
    -> FeatureMerger_59 [REQUESTOR]
    -> GeometryRemover_17
Note: Assign transmittance_id
FeatureMerger_59
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_23 [citydb.cityobject]
    UNMERGED_REQUESTOR -> FeatureWriter_23 [citydb.cityobject]
Note: Insert into CITYOBJECT
FeatureWriter_23
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_24 [citydb.ng3_device]
    citydb.cityobject -> Junction_103
Note: Insert into ng3_DEVICE
FeatureWriter_24
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_device -> AttributeKeeper_33
Note: Assign parent_id
Note: Only for debugging purpose!!!!!!!!
FeatureMerger_62
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_29
    UNMERGED_REQUESTOR -> AttributeCreator_36
Note: Rename StorageDevice
AttributeManager_29
    ATTR_TABLE:
      RENAME_SET_VALUE number_of_devices > num_of_devices (int64)
      RENAME_SET_VALUE heat_dissipation > heat_diss (real64)
      RENAME_SET_VALUE heat_dissipation_uom > heat_diss_uom (buffer)
      RENAME_SET_VALUE heat_dissipation_convective_fraction > heat_diss_conv (real64)
      RENAME_SET_VALUE heat_dissipation_convective_fraction_uom > heat_diss_conv_uom (buffer)
      RENAME_SET_VALUE heat_dissipation_latent_fraction > heat_diss_lat (real64)
      RENAME_SET_VALUE heat_dissipation_latent_fraction_uom > heat_diss_lat_uom (buffer)
      RENAME_SET_VALUE heat_dissipation_radiant_fraction > heat_diss_rad (real64)
      RENAME_SET_VALUE heat_dissipation_radiant_fraction_uom > heat_diss_rad_uom (buffer)
    USER_EXPOSED_ATTRIBUTES = co_id,table_name
    -> AttributeManager_30
Note: Rename StorageDevice attributes
AttributeManager_30
    ATTR_TABLE:
      RENAME_SET_VALUE battery_technology > batt_techn (buffer)
      RENAME_SET_VALUE battery_technology_codeSpace > batt_techn_codespace (buffer)
      RENAME_SET_VALUE preparation_temperature > preparation_temp (real64)
      RENAME_SET_VALUE preparation_temperature_uom > preparation_temp_uom (buffer)
      RENAME_SET_VALUE medium_codeSpace > medium_codespace (buffer)
      RENAME_SET_VALUE thermal_losses_factor > thm_losses_factor (real64)
      RENAME_SET_VALUE thermal_losses_factor_uom > thm_losses_factor_uom (buffer)
    -> FeatureMerger_25 [REQUESTOR]
Note: Assign transmittance_id
FeatureMerger_25
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_30 [citydb.cityobject]
    UNMERGED_REQUESTOR -> FeatureWriter_30 [citydb.cityobject]
Note: Insert into CITYOBJECT
FeatureWriter_30
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_31 [citydb.ng3_device]
    citydb.cityobject -> Junction_103
Note: Insert into ng3_DEVICE
FeatureWriter_31
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_device -> FeatureWriter_33 [citydb.ng3_storage_device]
Note: Insert into ng3_STORAGE_DEVICE
FeatureWriter_33
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_storage_device -> AttributeKeeper_33
Note: Assign parent_id
Note: Only for debugging purpose!!!!!!!!
FeatureMerger_64
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeManager_32
    UNMERGED_REQUESTOR -> AttributeCreator_15
Note: Rename Device attributes
AttributeManager_32
    ATTR_TABLE:
      RENAME_SET_VALUE number_of_devices > num_of_devices (int64)
      RENAME_SET_VALUE heat_dissipation > heat_diss (real64)
      RENAME_SET_VALUE heat_dissipation_uom > heat_diss_uom (buffer)
      RENAME_SET_VALUE heat_dissipation_convective_fraction > heat_diss_conv (real64)
      RENAME_SET_VALUE heat_dissipation_convective_fraction_uom > heat_diss_conv_uom (buffer)
      RENAME_SET_VALUE heat_dissipation_latent_fraction > heat_diss_lat (real64)
      RENAME_SET_VALUE heat_dissipation_latent_fraction_uom > heat_diss_lat_uom (buffer)
      RENAME_SET_VALUE heat_dissipation_radiant_fraction > heat_diss_rad (real64)
      RENAME_SET_VALUE heat_dissipation_radiant_fraction_uom > heat_diss_rad_uom (buffer)
    USER_EXPOSED_ATTRIBUTES = co_id,table_name
    -> AttributeManager_33
Note: Rename SolarCollector attributes
AttributeManager_33
    ATTR_TABLE:
      RENAME_SET_VALUE type_codeSpace > type_codespace (buffer)
      RENAME_SET_VALUE cell_type (buffer)
      RENAME_SET_VALUE cell_type_codeSpace > cell_type_codespace (buffer)
      RENAME_SET_VALUE optical_efficiency > opt_efficiency (real64)
      RENAME_SET_VALUE optical_efficiency_uom > opt_efficiency_uom (buffer)
      RENAME_SET_VALUE linear_heat_loss_coefficient > lin_heat_loss_coeff (real64)
      RENAME_SET_VALUE quadratic_heat_loss_coefficient > quad_heat_loss_coeff (real64)
    -> FeatureMerger_26 [REQUESTOR]
Note: Assign transmittance_id
FeatureMerger_26
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_34 [citydb.cityobject]
    UNMERGED_REQUESTOR -> FeatureWriter_34 [citydb.cityobject]
Note: Insert into CITYOBJECT
FeatureWriter_34
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> GeometryRemover_6
    citydb.cityobject -> AttributeKeeper_38
GeometryRemover_6
    REMOVE_COORDSYS = No
    -> FeatureMerger_120 [REQUESTOR]
AttributeKeeper_38
    CREATE_BULK_MODE_FEATURES = NO
    KEEP_ATTRS = id
    -> Deaggregator_3
    -> GeometryRemover_27
Deaggregator_3
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> AttributeFilter_7
AttributeFilter_7
    ATTR_NAME = _geometry_name
    ATTR_VALUES = <Empty>,<Missing>,<Null>,<Unfiltered>,referencePoint,lod2MultiSurface,lod3MultiSurface
    referencePoint -> FeatureMerger_120 [SUPPLIER]
    lod2MultiSurface -> SurfaceGeometryWriter_7
    lod3MultiSurface -> SurfaceGeometryWriter_8
FeatureMerger_120
    ATTR_ACCUM_MODE = Merge Supplier
    ATTR_CONFLICT_RES_LOOKUP = REQUESTOR_IF_CONFLICT
    IGNORE_NULLS = No
    JOIN_KEYS = @Value(id) @Value(id) AUTO
    MERGE_TYPE = Attributes and Geometry
    PROCESS_DUPS = NO
    REJECT_NULL_MISSING_KEYS = No
    SUPPLIERS_FIRST = No
    ATTR_CONFLICT_RES = Use Requestor
    MERGED -> GeometryRemover_24
    MERGED -> Junction_171
    UNMERGED_REQUESTOR -> GeometryRemover_24
    UNMERGED_REQUESTOR -> Junction_171
Junction_171
    -> Junction_103
Note: AttributeKeeper_29 : Input
Junction_103
    -> Junction_149
GeometryRemover_24
    REMOVE_COORDSYS = No
    -> FeatureMerger_124 [REQUESTOR]
Note: Assign surface_geometry_id
FeatureMerger_124
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureWriter_35 [citydb.ng3_device]
    UNMERGED_REQUESTOR -> FeatureWriter_35 [citydb.ng3_device]
Note: Insert into ng3_DEVICE
FeatureWriter_35
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_device -> FeatureWriter_37 [citydb.ng3_solar_collector]
    SUMMARY -> Junction_158
Note: Insert into ng3_SOLAR_COLLECTOR
FeatureWriter_37
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_solar_collector -> AttributeKeeper_33
AttributeKeeper_33
    CREATE_BULK_MODE_FEATURES = NO
    KEEP_ATTRS = gmlid,id
    -> Junction_86
Note: AttributeRenamer_61 : Input
Junction_86
    -> Junction_87
Note: AttributeKeeper_33 : Output
Junction_87
    -> AttributeRenamer_61
AttributeRenamer_61
    ATTR_TABLE:
      RENAME_SET_DEFAULT id > device_id
      RENAME_SET_DEFAULT gmlid > gml_parent_id
    KEEP_RENAMED_ONLY = no
    MISSING_INPUT_ATTRS = REMOVE
    -> FeatureMerger_57 [SUPPLIER]
Note: Assign parent_id
FeatureMerger_57
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> AttributeRenamer_64
    UNMERGED_REQUESTOR -> AttributeCreator_48
AttributeRenamer_64
    ATTR_TABLE = RENAME_SET_DEFAULT schedule_xlink_href > gml_link
    KEEP_RENAMED_ONLY = no
    MISSING_INPUT_ATTRS = REMOVE
    -> StringReplacer_28
Note: Trim # from XLinks
StringReplacer_28
    CASE = NO
    FIND_TEXT = #
    NO_MATCH = _FME_NO_OP_
    REGEXP = NO
    SRC_ATTRS = gml_link
    -> FeatureMerger_60 [REQUESTOR]
Note: Assign schedule_id
FeatureMerger_60
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeManager_27
    UNMERGED_REQUESTOR -> AttributeManager_27
Note: Rename DeviceOperation attributes
AttributeManager_27
    ATTR_TABLE = RENAME_SET_VALUE type_codeSpace > type_codespace (buffer)
    USER_EXPOSED_ATTRIBUTES = nrg3_is_ventilated,nrg3_library_code,thermal_conductivity_uom,specific_heat_capacity,co_parent_id,co_id,table_name
    -> FeatureWriter_28 [citydb.cityobject]
Note: Insert into CITYOBJECT
FeatureWriter_28
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.cityobject -> FeatureWriter_29 [citydb.ng3_device_operation]
Note: Insert into ng3_DEVICE_OPERATION
FeatureWriter_29
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: Preliminary 3DCityDB checks
AttributeCreator_57
    ATTR_TABLE = SET_TO sql_statement (varchar(94)) = SELECT version, major_version, minor_version, minor_revision FROM citydb_pkg.citydb_version();
    -> SQLExecutor_14 [INITIATOR]
Note: Check versin of 3DCityDB
SQLExecutor_14
    COMBINE_ATTRS = Result Attributes Only
    COMBINE_GEOM = Initiator Geometry Only
    COORDSYS = EPSG:28992
    DATASET = Shared 3DCityDB connection
    EXPOSED_ATTRIBUTE_LIST = version,major_version,minor_version,minor_revision
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    SQL_STATEMENT = @Value(sql_statement)
    RESULT -> Tester_4
Tester_4
    BOOL_OP = OR
    TEST_CLAUSE = TEST @Value(major_version) = 4
    TEST_MODE = TEST
    PASSED -> Tester_3
    FAILED -> Terminator_5
Terminator_5
    MESSAGE:
      Your 3DCityDB major version is @Value(major_version).
      This FME Workbench requires major version 4.
Tester_3
    BOOL_OP = COMPOSITE
    COMPOSITE_TEST = 1 AND 2
    TEST_CLAUSE:
      TEST @Value(minor_version) = 4
      TEST @Value(minor_revision) >= 1
    TEST_MODE = TEST
    PASSED -> AttributeCreator_55
    FAILED -> Terminator_4
Terminator_4
    MESSAGE:
      Your 3DCityDB version is @Value(version).
      You need version 4.4.1 or higher
AttributeCreator_55
    ATTR_TABLE = SET_TO sql_statement (varchar(200)) = SELECT EXISTS (SELECT 1 FROM pg_catalog.pg_namespace WHERE nspname = '$(citydb_schema)') AS test1;
    -> SQLExecutor_12 [INITIATOR]
Note: Check existence of selected citydb
SQLExecutor_12
    COMBINE_ATTRS = Result Attributes Only
    COMBINE_GEOM = Initiator Geometry Only
    COORDSYS = EPSG:28992
    DATASET = Shared 3DCityDB connection
    EXPOSED_ATTRIBUTE_LIST = test1
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    SQL_STATEMENT = @Value(sql_statement)
    RESULT -> Tester_2
Tester_2
    BOOL_OP = OR
    TEST_CLAUSE = TEST @Value(test1) = t
    TEST_MODE = TEST
    PASSED -> AttributeCreator_54
    FAILED -> Terminator_3
Terminator_3
    MESSAGE = Schema '$(citydb_schema)' does not exist in the current database.
AttributeCreator_54
    ATTR_TABLE = SET_TO sql_statement (varchar(200)) = SELECT count(*) AS test2 FROM $(citydb_schema).ade WHERE name = 'Energy ADE' AND db_prefix = 'ng3' AND version = '$(Energy_ADE_3.0_version)';
    -> SQLExecutor_10 [INITIATOR]
Note: Check Energy ADE version
SQLExecutor_10
    COMBINE_ATTRS = Result Attributes Only
    COMBINE_GEOM = Initiator Geometry Only
    COORDSYS = EPSG:28992
    DATASET = Shared 3DCityDB connection
    EXPOSED_ATTRIBUTE_LIST = test2
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    SQL_STATEMENT = @Value(sql_statement)
    RESULT -> AttributeFilter_3
AttributeFilter_3
    ATTR_NAME = test2
    ATTR_VALUES = <Empty>,<Missing>,<Null>,<Unfiltered>,1
    <UNFILTERED> -> Terminator
    1 -> AttributeCreator_53
    1 -> AttributeKeeper_4
Terminator
    MESSAGE:
      The Energy ADE 2.0 is either not installed or not available
      in the required version (i.e. $(Energy_ADE_3.0_version)).
AttributeCreator_53 [off]
    ATTR_TABLE = SET_TO sql_statement (varchar(200)) = SELECT count(*) AS test3 FROM $(citydb_schema).cityobject WHERE objectclass_id IN (SELECT id FROM $(citydb_schema).objectclass WHERE is_ade_class = 0);
    -> SQLExecutor_11 [INITIATOR]
Note: Are there data in the 3DCityDB?
SQLExecutor_11
    COMBINE_ATTRS = Result Attributes Only
    COMBINE_GEOM = Initiator Geometry Only
    COORDSYS = EPSG:28992
    DATASET = Shared 3DCityDB connection
    EXPOSED_ATTRIBUTE_LIST = test3
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    SQL_STATEMENT = @Value(sql_statement)
    RESULT -> Tester
Tester
    BOOL_OP = OR
    TEST_CLAUSE = TEST @Value(test3) = 0
    TEST_MODE = TEST
    PASSED -> Terminator_2
    FAILED -> AttributeKeeper_4
Terminator_2
    MESSAGE:
      There are no CityGML data in schema '$(citydb_schema)'.
      Please use the 3DCityDB Importer for this task.
AttributeKeeper_4
    CREATE_BULK_MODE_FEATURES = NO
    -> AttributeCreator_38

Bookmark: Get sequence values
AttributeCreator_38
    ATTR_TABLE:
      SET_TO sql_statement (varchar(200)) = -- Data types
        SELECT $(citydb_schema).del_ng3_suitability(id) FROM $(citydb_schema).ng3_suitability;
        SELECT $(citydb_schema).del_ng3_optical_property(id) FROM $(citydb_schema).ng3_optical_property;
        SELECT $(citydb_schema).del_ng3_qualified_attribute(id) FROM $(citydb_schema).ng3_qualified_attribute;

        -- Time Series module
        SELECT $(citydb_schema).del_ng3_time_series(co.id) FROM $(citydb_schema).cityobject AS co JOIN $(citydb_schema).objectclass AS o ON (co.objectclass_id = o.id)
        	WHERE o.classname IN ('RegularTimeSeries', 'RegularTimeSeriesFile', 'TypicalValuesTimeSeries', 'TypicalValuesTimeSeriesFile', 'SensorConnection');

        -- Schedules module
        SELECT $(citydb_schema).del_ng3_schedule(co.id) FROM $(citydb_schema).cityobject AS co JOIN $(citydb_schema).objectclass AS o ON (co.objectclass_id = o.id)
        	WHERE o.classname IN ('AtomicSchedule', 'DualValueSchedule', 'CompositeSchedule');
        SELECT $(citydb_schema).del_ng3_schedule_component(co.id) FROM $(citydb_schema).cityobject AS co JOIN $(citydb_schema).objectclass AS o ON (co.objectclass_id = o.id AND o.classname='ScheduleComponent');
        SELECT $(citydb_schema).del_ng3_library(co.id) FROM $(citydb_schema).cityobject AS co JOIN $(citydb_schema).objectclass AS o ON (co.objectclass_id = o.id AND o.classname='ScheduleLibrary');

        -- Layered Construction module
        SELECT $(citydb_schema).del_ng3_material(co.id) FROM $(citydb_schema).cityobject AS co JOIN $(citydb_schema).objectclass AS o ON (co.objectclass_id = o.id)
        	WHERE o.classname IN ('Gas', 'SolidMaterial');
        SELECT $(citydb_schema).del_ng3_layer(co.id) FROM $(citydb_schema).cityobject AS co JOIN $(citydb_schema).objectclass AS o ON (co.objectclass_id = o.id)
        	WHERE o.classname IN ('Layer');
        SELECT $(citydb_schema).del_ng3_layered_construction(co.id) FROM $(citydb_schema).cityobject AS co JOIN $(citydb_schema).objectclass AS o ON (co.objectclass_id = o.id)
        	WHERE o.classname IN ('LayeredConstruction', 'ReverseLayeredConstruction');
        SELECT $(citydb_schema).del_ng3_library(co.id) FROM $(citydb_schema).cityobject AS co JOIN $(citydb_schema).objectclass AS o ON (co.objectclass_id = o.id)
        	WHERE o.classname IN ('MaterialLibrary', 'LayeredConstructionLibrary');

        -- Resource module
        SELECT $(citydb_schema).del_ng3_resource(co.id) FROM $(citydb_schema).cityobject AS co JOIN $(citydb_schema).objectclass AS o ON (co.objectclass_id = o.id)
        	WHERE o.classname IN ('Energy', 'Water', 'Waste', 'Food', 'UrbanSpace', 'ConstructionMaterial', 'OtherResource');

        -- Weather Station module
        SELECT $(citydb_schema).del_cityobject(co.id) FROM $(citydb_schema).cityobject AS co JOIN $(citydb_schema).objectclass AS o ON (co.objectclass_id = o.id AND o.classname='WeatherStation');

        -- A bit of Core module
        SELECT $(citydb_schema).del_ng3_ctyobj_relation(id) FROM $(citydb_schema).ng3_ctyobj_relation;
        SELECT $(citydb_schema).del_ng3_weather_data(co.id) FROM $(citydb_schema).cityobject AS co JOIN $(citydb_schema).objectclass AS o ON (co.objectclass_id = o.id AND o.classname='WeatherData');
        SELECT $(citydb_schema).del_ng3_utl_ntw_connection(co.id) FROM $(citydb_schema).cityobject AS co JOIN $(citydb_schema).objectclass AS o ON (co.objectclass_id = o.id AND o.classname='UtilityNetworkConnection');
        SELECT $(citydb_schema).del_ng3_energy_perf_cert(co.id) FROM $(citydb_schema).cityobject AS co JOIN $(citydb_schema).objectclass AS o ON (co.objectclass_id = o.id AND o.classname='EnergyPerformanceCertificate');
        SELECT $(citydb_schema).del_ng3_refurbishment_measure(co.id) FROM $(citydb_schema).cityobject AS co JOIN $(citydb_schema).objectclass AS o ON (co.objectclass_id = o.id AND o.classname='RefurbishmentMeasure');

        -- Urban Function Area module
        SELECT $(citydb_schema).del_ng3_urban_function_area(co.id) FROM $(citydb_schema).cityobject AS co JOIN $(citydb_schema).objectclass AS o ON (co.objectclass_id = o.id AND o.classname='UrbanFunctionArea');

        -- Devices module
        SELECT $(citydb_schema).del_ng3_storage_device(co.id) FROM $(citydb_schema).cityobject AS co JOIN $(citydb_schema).objectclass AS o ON (co.objectclass_id = o.id)
        	WHERE o.classname IN ('ThermalStorageDevice', 'ElectricalStorageDevice');
        SELECT $(citydb_schema).del_ng3_solar_collector(co.id) FROM $(citydb_schema).cityobject AS co JOIN $(citydb_schema).objectclass AS o ON (co.objectclass_id = o.id)
        	WHERE o.classname IN ('GenericSolarCollector', 'PhotovoltaicCollector', 'SolarThermalCollector', 'PhotovoltaicThermalCollector');
        SELECT $(citydb_schema).del_ng3_device(co.id) FROM $(citydb_schema).cityobject AS co JOIN $(citydb_schema).objectclass AS o ON (co.objectclass_id = o.id)
        	WHERE o.classname IN ('Boiler', 'LightingDevice', 'GenericDevice', 'GenericElectricalDevice', 'MovableShadingDevice');

        -- Delete the PartyWalls that may be used for Buildings and not for ThermalZones
        --SELECT $(citydb_schema).del_thematic_surface(co.id) FROM $(citydb_schema).thematic_surface AS co JOIN $(citydb_schema).objectclass AS o ON (co.objectclass_id = o.id AND o.classname='PartyWallSurface')
        --	WHERE co.building_id IS NOT NULL;

        -- Occupancy module
        SELECT $(citydb_schema).del_ng3_occupants(co.id) FROM $(citydb_schema).cityobject AS co JOIN $(citydb_schema).objectclass AS o ON (co.objectclass_id = o.id AND o.classname='Occupants');
        SELECT $(citydb_schema).del_ng3_building_partition(co.id) FROM $(citydb_schema).cityobject AS co JOIN $(citydb_schema).objectclass AS o ON (co.objectclass_id = o.id AND o.classname='BuildingUnit');
        SELECT $(citydb_schema).del_ng3_building_partition(co.id) FROM $(citydb_schema).cityobject AS co JOIN $(citydb_schema).objectclass AS o ON (co.objectclass_id = o.id AND o.classname='UsageZone');

        -- Building physics module
        SELECT $(citydb_schema).del_thematic_surface(co.id) FROM $(citydb_schema).cityobject AS co JOIN $(citydb_schema).objectclass AS o ON (co.objectclass_id = o.id)
        	WHERE o.classname IN ('PartyWallSurface', 'BasementCeilingSurface', 'IntermediateFloorSurface', 'AtticFloorSurface');
        -- dependent openings used for thermal boundaries will be dropped automatically on cascade
        SELECT $(citydb_schema).del_ng3_building_partition(co.id) FROM $(citydb_schema).cityobject AS co JOIN $(citydb_schema).objectclass AS o ON (co.objectclass_id = o.id AND o.classname='ThermalZone');

        -- A bit of Core module: Delete only ADE data from the ng3 tables
        SELECT $(citydb_schema).del_ng3_opening(id) FROM $(citydb_schema).ng3_opening;
        SELECT $(citydb_schema).del_ng3_thematic_surface(id) FROM $(citydb_schema).ng3_thematic_surface;
        SELECT $(citydb_schema).del_ng3_building(id) FROM $(citydb_schema).ng3_building;
        SELECT $(citydb_schema).del_ng3_cityobject(id) FROM $(citydb_schema).ng3_cityobject;

        -- Do something at the end
        SELECT 1 AS id;
    -> SQLExecutor_2 [INITIATOR]
Note: Clean up all Energy ADE 3.0 stuff, but leave vanilla CityGML data.
SQLExecutor_2
    ATTR_IGNORE_NULLS = No
    COMBINE_ATTRS = Keep Initiator Attributes if Conflict
    COMBINE_GEOM = Initiator Geometry Only
    COORDSYS = EPSG:28992
    DATASET = Shared 3DCityDB connection
    EXPOSED_ATTRIBUTE_LIST = id
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    SQL_STATEMENT = @Value(sql_statement)
    INITIATOR -> XLinkUpdater_2
Note: Update the is_xlink attribute in the surface_geometry table
XLinkUpdater_2
    cp_schema_name = $(citydb_schema)
    -> AttributeCreator_39
AttributeCreator_39
    ATTR_TABLE = SET_TO sql_statement (varchar(200)) = SELECT sequence_name FROM information_schema.sequences WHERE sequence_schema='$(citydb_schema)';
    -> SQLExecutor_3 [INITIATOR]
Note: Get list of sequences in the selected citydb_schema
SQLExecutor_3
    ATTR_IGNORE_NULLS = No
    COMBINE_ATTRS = Keep Initiator Attributes if Conflict
    COMBINE_GEOM = Initiator Geometry Only
    COORDSYS = EPSG:28992
    DATASET = Shared 3DCityDB connection
    EXPOSED_ATTRIBUTE_LIST = sequence_name
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> AttributeFilter
Note: Adjust the names of some sequences
AttributeFilter
    ATTR_NAME = sequence_name
    ATTR_VALUES = <Empty>,<Missing>,<Null>,<Unfiltered>,cityobject_genericatt_seq,external_ref_seq,index_table_id_seq
    <UNFILTERED> -> AttributeCreator
    cityobject_genericatt_seq -> AttributeCreator_3
    external_ref_seq -> AttributeCreator_2
    index_table_id_seq -> AttributeCreator_4
AttributeCreator
    ATTR_TABLE:
      SET_TO schema_name (varchar(200)) = $(citydb_schema)
      SET_TO table_name (varchar(200)) = @Value(sequence_name)
    -> StringReplacer
StringReplacer
    CASE = NO
    FIND_TEXT = _seq
    NO_MATCH = _FME_NO_OP_
    REGEXP = NO
    SRC_ATTRS = table_name
    -> Junction_132
AttributeCreator_3
    ATTR_TABLE:
      SET_TO schema_name (varchar(200)) = $(citydb_schema)
      SET_TO table_name (varchar(24)) = cityobject_genericattrib
    -> Junction_132
AttributeCreator_2
    ATTR_TABLE:
      SET_TO schema_name (varchar(200)) = $(citydb_schema)
      SET_TO table_name (varchar(18)) = external_reference
    -> Junction_132
AttributeCreator_4
    ATTR_TABLE:
      SET_TO schema_name (varchar(200)) = $(citydb_schema)
      SET_TO table_name (varchar(18)) = index_table
    -> Junction_132
Junction_132
    -> SQLExecutor [INITIATOR]
SQLExecutor
    ATTR_IGNORE_NULLS = Yes
    COMBINE_ATTRS = Keep Initiator Attributes if Conflict
    COMBINE_GEOM = Initiator Geometry Only
    COORDSYS = EPSG:28992
    DATASET = Shared 3DCityDB connection
    EXPOSED_ATTRIBUTE_LIST = curr_val
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT:
      WITH s AS (SELECT max(t.id) AS max_id FROM @Value(schema_name).@Value(table_name) AS t)
      SELECT CASE WHEN s.max_id IS NULL     THEN setval('@Value(schema_name).@Value(sequence_name)'::regclass, 0, true)
               WHEN s.max_id IS NOT NULL THEN setval('@Value(schema_name).@Value(sequence_name)'::regclass, s.max_id, true) END AS curr_val
      FROM s;
    RESULT -> AttributeFilter_2
AttributeFilter_2
    ATTR_NAME = table_name
    ATTR_VALUES = <Empty>,<Missing>,<Null>,<Unfiltered>,address,ade,appearance,citymodel,cityobject,cityobject_genericattrib,external_reference,grid_coverage,implicit_geometry,index_table,ng3_ctyobj_relation,ng3_optical_property,ng3_qualified_attribute,ng3_suitability,schema,surface_data,surface_geometry,tex_image
    appearance -> Counter_3
    cityobject -> Counter
    cityobject_genericattrib -> Counter_11
    external_reference -> Counter_10
    ng3_ctyobj_relation -> Counter_4
    ng3_optical_property -> Counter_5
    ng3_qualified_attribute -> Counter_6
    ng3_suitability -> Counter_7
    surface_data -> Counter_8
    surface_geometry -> Counter_9
Note: Create FME global counters that are internally named as the table they refer to
Counter_3
    CNT_ATTR = _count
    DOMAIN = @Value(table_name)
    SCOPE = Global
    START = @Value(curr_val)
    -> Aggregator
Counter
    CNT_ATTR = _count
    DOMAIN = @Value(table_name)
    SCOPE = Global
    START = @Value(curr_val)
    -> Aggregator
Counter_11
    CNT_ATTR = _count
    DOMAIN = @Value(table_name)
    SCOPE = Global
    START = @Value(curr_val)
    -> Aggregator
Counter_4
    CNT_ATTR = _count
    DOMAIN = @Value(table_name)
    SCOPE = Global
    START = @Value(curr_val)
    -> Aggregator
Counter_10
    CNT_ATTR = _count
    DOMAIN = @Value(table_name)
    SCOPE = Global
    START = @Value(curr_val)
    -> Aggregator
Counter_5
    CNT_ATTR = _count
    DOMAIN = @Value(table_name)
    SCOPE = Global
    START = @Value(curr_val)
    -> Aggregator
Counter_8
    CNT_ATTR = _count
    DOMAIN = @Value(table_name)
    SCOPE = Global
    START = @Value(curr_val)
    -> Aggregator
Counter_6
    CNT_ATTR = _count
    DOMAIN = @Value(table_name)
    SCOPE = Global
    START = @Value(curr_val)
    -> Aggregator
Counter_9
    CNT_ATTR = _count
    DOMAIN = @Value(table_name)
    SCOPE = Global
    START = @Value(curr_val)
    -> Aggregator
Counter_7
    CNT_ATTR = _count
    DOMAIN = @Value(table_name)
    SCOPE = Global
    START = @Value(curr_val)
    -> Aggregator
Aggregator
    ACCUM_ATTRS_NAME = Drop Incoming Attributes
    AGGREGATE_TYPE = Homogeneous Collection (If Possible)
    MODE = Geometry - Assemble One Level
    SEP = ,
    AGGREGATE -> AttributeKeeper
AttributeKeeper
    CREATE_BULK_MODE_FEATURES = NO
    -> Junction_192

Bookmark: Read existing objects in the database
Junction_192
    -> AttributeCreator_13
    -> AttributeCreator_16
    -> AttributeCreator_14
    -> AttributeCreator_34
    -> AttributeCreator_35
AttributeCreator_16
    ATTR_TABLE = SET_TO sql_statement (varchar(200)) = SELECT id, classname, tablename FROM $(citydb_schema).objectclass;
    -> SQLExecutor_6 [INITIATOR]
SQLExecutor_6
    COMBINE_ATTRS = Result Attributes Only
    COMBINE_GEOM = Initiator Geometry Only
    DATASET = Shared 3DCityDB connection
    EXPOSED_ATTRIBUTE_LIST = id,classname,tablename
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> AttributeKeeper_80
AttributeKeeper_80
    CREATE_BULK_MODE_FEATURES = NO
    KEEP_ATTRS = id,classname,tablename
    -> AttributeRenamer_3
AttributeRenamer_3
    ATTR_TABLE:
      RENAME_SET_DEFAULT classname > objectclass_name
      RENAME_SET_DEFAULT id > objectclass_id
      RENAME_SET_DEFAULT tablename > table_name
    KEEP_RENAMED_ONLY = no
    MISSING_INPUT_ATTRS = REMOVE
    -> Junction_193
Junction_193
    -> FeatureMerger_5 [SUPPLIER]
    -> FeatureMerger_15 [SUPPLIER]
    -> FeatureMerger_16 [SUPPLIER]
    -> FeatureMerger_75 [SUPPLIER]
    -> Junction_17
AttributeCreator_13
    ATTR_TABLE = SET_TO sql_statement (varchar(200)) = SELECT id, objectclass_id, gmlid FROM $(citydb_schema).cityobject;
    -> SQLExecutor_4 [INITIATOR]
Note: CITYOBJECT
SQLExecutor_4
    COMBINE_ATTRS = Result Attributes Only
    COMBINE_GEOM = Initiator Geometry Only
    DATASET = Shared 3DCityDB connection
    EXPOSED_ATTRIBUTE_LIST = id,objectclass_id,gmlid
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> FeatureMerger_5 [REQUESTOR]
FeatureMerger_5
    ATTR_ACCUM_MODE = Merge Supplier
    ATTR_CONFLICT_RES_LOOKUP = REQUESTOR_IF_CONFLICT
    IGNORE_NULLS = No
    JOIN_KEYS = @Value(objectclass_id) @Value(objectclass_id) AUTO
    MERGE_TYPE = Attributes Only
    PROCESS_DUPS = NO
    REJECT_NULL_MISSING_KEYS = No
    SUPPLIERS_FIRST = No
    ATTR_CONFLICT_RES = Use Requestor
    MERGED -> Junction_172
Junction_172
    -> Junction_47
AttributeCreator_14
    ATTR_TABLE = SET_TO sql_statement (varchar(200)) = SELECT id, gmlid FROM $(citydb_schema).address;
    -> SQLExecutor_5 [INITIATOR]
Note: ADDRESS
SQLExecutor_5
    COMBINE_ATTRS = Result Attributes Only
    COMBINE_GEOM = Initiator Geometry Only
    DATASET = Shared 3DCityDB connection
    EXPOSED_ATTRIBUTE_LIST = id,gmlid
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> AttributeCreator_10
Note: Address
AttributeCreator_10
    ATTR_TABLE = SET_TO objectclass_name (varchar(7)) = Address
    -> FeatureMerger_15 [REQUESTOR]
FeatureMerger_15
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Junction_173
Junction_173
    -> Junction_165
AttributeCreator_34
    ATTR_TABLE = SET_TO sql_statement (varchar(200)) = SELECT id, gmlid, theme, cityobject_id FROM $(citydb_schema).appearance;
    -> SQLExecutor_7 [INITIATOR]
Note: APPEARANCE
SQLExecutor_7
    COMBINE_ATTRS = Result Attributes Only
    COMBINE_GEOM = Initiator Geometry Only
    DATASET = Shared 3DCityDB connection
    EXPOSED_ATTRIBUTE_LIST = id,gmlid,objectclass_id
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> AttributeCreator_11
Note: Appearance
AttributeCreator_11
    ATTR_TABLE = SET_TO objectclass_name (varchar(10)) = Appearance
    -> FeatureMerger_16 [REQUESTOR]
FeatureMerger_16
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Junction_174
Junction_174
    -> Junction_163
AttributeCreator_35
    ATTR_TABLE = SET_TO sql_statement (varchar(200)) = SELECT id, objectclass_id, gmlid FROM $(citydb_schema).surface_data;
    -> SQLExecutor_8 [INITIATOR]
Note: SURFACE_DATA
SQLExecutor_8
    COMBINE_ATTRS = Result Attributes Only
    COMBINE_GEOM = Initiator Geometry Only
    DATASET = Shared 3DCityDB connection
    EXPOSED_ATTRIBUTE_LIST = id,objectclass_id,gmlid
    FORMAT = POSTGRES
    OUTPUT_FEATURES = DATA_ONLY
    POSTGRES_CREATE_FEATURE_TABLES_FROM_DATA = Yes
    POSTGRES_NAMED_CONNECTION = eade2_test.citydb @ localhost (pg16) AS postgres
    POSTGRES_QUERY_FEATURE_TYPES_FOR_MERGE_FILTERS = Yes
    POSTGRES_READ_TIME_WITH_TIMEZONE = Yes
    SQL_STATEMENT = @Value(sql_statement)
    RESULT -> FeatureMerger_75 [REQUESTOR]
FeatureMerger_75
    ATTR_ACCUM_MODE = Merge Supplier
    ATTR_CONFLICT_RES_LOOKUP = REQUESTOR_IF_CONFLICT
    IGNORE_NULLS = No
    JOIN_KEYS = @Value(objectclass_id) @Value(objectclass_id) AUTO
    MERGE_TYPE = Attributes Only
    PROCESS_DUPS = NO
    REJECT_NULL_MISSING_KEYS = No
    SUPPLIERS_FIRST = No
    ATTR_CONFLICT_RES = Use Requestor
    MERGED -> AttributeFilter_10
AttributeFilter_10
    ATTR_NAME = objectclass_name
    ATTR_VALUES = <Empty>,<Missing>,<Null>,<Unfiltered>,X3DMaterial
    X3DMaterial -> Junction_175
Junction_175
    -> Junction_164

Bookmark: Material
Junction_10
    -> ADE_Feature_editor_1 [objectclass_name_list]
    -> ADE_CityObject_editor [objectclass_name_list]
    -> ADE_Feature_editor_2 [objectclass_name_list]
nrg3_MaterialLibrary (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_type xml_buffer,
      nrg3_type_codeSpace xml_buffer, nrg3_source xml_buffer, nrg3_author xml_buffer, nrg3_library_member{}.xlink_href xml_buffer
    -> ADE_CityObject_editor [ADE_CityObject]
nrg3_Gas (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_is_ventilated xml_boolean, nrg3_r_value xml_real64, nrg3_r_value_units xml_buffer
    -> ADE_Feature_editor_1 [ADE_Feature]
nrg3_SolidMaterial (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_thermal_conductivity xml_real64, nrg3_thermal_conductivity_units xml_buffer, nrg3_density xml_real64, nrg3_density_units xml_buffer, nrg3_specific_heat_capacity xml_real64, nrg3_specific_heat_capacity_units xml_buffer, nrg3_permeance xml_real64, nrg3_permeance_units xml_buffer, nrg3_porosity xml_real64, nrg3_porosity_units xml_buffer, nrg3_embodied_energy xml_real64, nrg3_embodied_energy_units xml_buffer, nrg3_embodied_carbon xml_real64, nrg3_embodied_carbon_units xml_buffer
    -> ADE_Feature_editor_2 [ADE_Feature]

Bookmark: Layered Construction
Junction_12
    -> ADE_Feature_editor_5 [objectclass_name_list]
    -> ADE_Feature_editor_3 [objectclass_name_list]
    -> Junction_57
    -> ADE_CityObject_editor_2 [objectclass_name_list]
    -> ADE_Feature_editor_4 [objectclass_name_list]
nrg3_LayeredConstructionLibrary (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_type xml_buffer,
      nrg3_type_codeSpace xml_buffer, nrg3_source xml_buffer, nrg3_author xml_buffer, nrg3_library_member{}.xlink_href xml_buffer
    -> ADE_CityObject_editor_2 [ADE_CityObject]
nrg3_LayeredConstruction (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_u_value xml_real64, nrg3_u_value_units xml_buffer, nrg3_g_value xml_real64, nrg3_g_value_units xml_buffer, nrg3_glazing_ratio xml_real64, nrg3_glazing_ratio_units xml_buffer, nrg3_emissivity{}.nrg3_emissivity_nrg3_fraction xml_real64, nrg3_emissivity{}.nrg3_emissivity_nrg3_fraction_units xml_buffer, nrg3_emissivity{}.nrg3_emissivity_nrg3_surface xml_char(7), nrg3_reflectance{}.nrg3_reflectance_nrg3_fraction xml_real64, nrg3_reflectance{}.nrg3_reflectance_nrg3_fraction_units xml_buffer, nrg3_reflectance{}.nrg3_reflectance_nrg3_surface xml_char(7), nrg3_reflectance{}.nrg3_reflectance_nrg3_wavelength_range xml_char(8), nrg3_transmittance{}.nrg3_transmittance_nrg3_fraction xml_real64, nrg3_transmittance{}.nrg3_transmittance_nrg3_fraction_units xml_buffer, nrg3_transmittance{}.nrg3_transmittance_nrg3_wavelength_range xml_char(8), nrg3_layer{}.xlink_href xml_buffer
    -> ADE_Feature_editor_4 [ADE_Feature]
nrg3_ReverseLayeredConstruction (reader CITYGML_2)
    attributes: citygml_target_uri xml_buffer, citygml_feature_role xml_buffer, citygml_feature_role_attr_name xml_buffer, citygml_feature_role_attr_val xml_buffer, gml_description xml_buffer, gml_name xml_buffer, nrg3_base_layered_construction_xlink_href xml_buffer
    -> ADE_Feature_editor_5 [ADE_Feature]
nrg3_Layer (reader CITYGML_2)
    attributes: citygml_target_uri xml_buffer, citygml_feature_role xml_buffer, citygml_feature_role_attr_name xml_buffer, citygml_feature_role_attr_val xml_buffer, gml_description xml_buffer, gml_name xml_buffer, nrg3_thickness xml_real64, nrg3_thickness_units xml_buffer, nrg3_material_xlink_href xml_buffer
    -> ADE_Feature_editor_3 [ADE_Feature]

Bookmark: OPTICAL PROPERTY
Junction_57
    -> FeatureMerger_35 [SUPPLIER]
Junction_20
    -> AttributeRenamer_22
AttributeRenamer_22
    ATTR_TABLE = RENAME_SET_DEFAULT id > layered_construction_id
    KEEP_RENAMED_ONLY = no
    MISSING_INPUT_ATTRS = REMOVE
    -> AttributeKeeper_20
    -> AttributeKeeper_21
    -> AttributeKeeper_22
AttributeKeeper_20
    CREATE_BULK_MODE_FEATURES = NO
    KEEP_ATTRS = layered_construction_id
    KEEP_LIST = emissivity{}
    -> ListExploder_5
ListExploder_5
    ATTR_ACCUM_MODE = Merge List Attributes
    ATTR_CONFLICT_RES_LOOKUP = INCOMING_IF_CONFLICT
    LIST_ATTR = emissivity{}
    ATTR_CONFLICT_RES = Use List Attribute Values
    ELEMENTS -> BulkAttributeRenamer_11
BulkAttributeRenamer_11
    ATTRCHOICE_ACTION = NONPROTECTEDFME
    CASE_DISP = NO
    MODE_CHOICE = RENAME
    PATTERN_ACTION_DISP = STRINGREPLACE
    REPLACE_PATTERN = emissivity_
    ATTRCHOICE = All Attributes
    -> AttributeCreator_22
Note: Add objectclass_name
AttributeCreator_22
    ATTR_TABLE = SET_TO objectclass_name (varchar(15)) = Emissivity
    -> FeatureMerger_35 [REQUESTOR]
AttributeKeeper_21
    CREATE_BULK_MODE_FEATURES = NO
    KEEP_ATTRS = layered_construction_id
    KEEP_LIST = reflectance{}
    -> ListExploder_6
ListExploder_6
    ATTR_ACCUM_MODE = Merge List Attributes
    ATTR_CONFLICT_RES_LOOKUP = INCOMING_IF_CONFLICT
    LIST_ATTR = reflectance{}
    ATTR_CONFLICT_RES = Use List Attribute Values
    ELEMENTS -> BulkAttributeRenamer_12
BulkAttributeRenamer_12
    ATTRCHOICE_ACTION = NONPROTECTEDFME
    CASE_DISP = NO
    MODE_CHOICE = RENAME
    PATTERN_ACTION_DISP = STRINGREPLACE
    REPLACE_PATTERN = reflectance_
    ATTRCHOICE = All Attributes
    -> AttributeCreator_23
Note: Add objectclass_name
AttributeCreator_23
    ATTR_TABLE = SET_TO objectclass_name (varchar(15)) = Reflectance
    -> FeatureMerger_35 [REQUESTOR]
AttributeKeeper_22
    CREATE_BULK_MODE_FEATURES = NO
    KEEP_ATTRS = layered_construction_id
    KEEP_LIST = transmittance{}
    -> ListExploder_7
ListExploder_7
    ATTR_ACCUM_MODE = Merge List Attributes
    ATTR_CONFLICT_RES_LOOKUP = INCOMING_IF_CONFLICT
    LIST_ATTR = transmittance{}
    ATTR_CONFLICT_RES = Use List Attribute Values
    ELEMENTS -> BulkAttributeRenamer_13
BulkAttributeRenamer_13
    ATTRCHOICE_ACTION = NONPROTECTEDFME
    CASE_DISP = NO
    MODE_CHOICE = RENAME
    PATTERN_ACTION_DISP = STRINGREPLACE
    REPLACE_PATTERN = transmittance_
    ATTRCHOICE = All Attributes
    -> AttributeCreator_24
Note: Add objectclass_name
AttributeCreator_24
    ATTR_TABLE = SET_TO objectclass_name (varchar(15)) = Transmittance
    -> FeatureMerger_35 [REQUESTOR]
FeatureMerger_35
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter_7
Sorter_7
    SORT_PARM = layered_construction_id NATURAL ASCENDING objectclass_id NATURAL ASCENDING
    SORTED -> Counter_18
Counter_18
    CNT_ATTR = id
    DOMAIN = @Value(table_name)
    SCOPE = Global
    START = 0
    -> FeatureWriter_8 [citydb.ng3_optical_property]
Note: Insert into ng3_OPTICAL_PROPERTIES
FeatureWriter_8
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: Schedules
Junction_15
    -> ADE_Feature_editor_7 [objectclass_name_list]
    -> ADE_CityObject_editor_3 [objectclass_name_list]
    -> ADE_Feature_editor_6 [objectclass_name_list]
nrg3_ScheduleComponent (reader CITYGML_2)
    attributes: citygml_target_uri xml_buffer, citygml_feature_role xml_buffer, citygml_feature_role_attr_name xml_buffer, citygml_feature_role_attr_val xml_buffer, gml_description xml_buffer, gml_name xml_buffer, nrg3_type xml_buffer, nrg3_type_codeSpace xml_buffer, nrg3_repetitions xml_int64, nrg3_additional_gap xml_real64, nrg3_additional_gap_unit xml_buffer, nrg3_additional_gap_radix xml_uint64, nrg3_additional_gap_factor xml_int64, nrg3_schedule_component_member_xlink_href xml_buffer
    -> ADE_Feature_editor_7 [ADE_Feature]
nrg3_ScheduleLibrary (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_type xml_buffer,
      nrg3_type_codeSpace xml_buffer, nrg3_source xml_buffer, nrg3_author xml_buffer, nrg3_library_member{}.xlink_href xml_buffer
    -> ADE_CityObject_editor_3 [ADE_CityObject]
nrg3_DualValueSchedule (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_type xml_buffer, nrg3_type_codeSpace xml_buffer, nrg3_start_time xml_time, nrg3_start_day xml_int64, nrg3_start_month xml_int64, nrg3_start_year xml_int64, nrg3_temporal_extent xml_real64, nrg3_temporal_extent_unit xml_buffer, nrg3_temporal_extent_radix xml_uint64, nrg3_temporal_extent_factor xml_int64, nrg3_idle_value xml_real64, nrg3_idle_value_units xml_buffer, nrg3_usage_value xml_real64, nrg3_usage_value_units xml_buffer, nrg3_start_usage_time xml_time, nrg3_end_usage_time xml_time
    -> ADE_Feature_editor_6 [ADE_Feature]
nrg3_AtomicSchedule (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_type xml_buffer, nrg3_type_codeSpace xml_buffer, nrg3_start_time xml_time, nrg3_start_day xml_int64, nrg3_start_month xml_int64, nrg3_start_year xml_int64, nrg3_temporal_extent xml_real64, nrg3_temporal_extent_unit xml_buffer, nrg3_temporal_extent_radix xml_uint64, nrg3_temporal_extent_factor xml_int64, nrg3_constant_value xml_real64, nrg3_constant_value_units xml_buffer, nrg3_time_series_xlink_href xml_buffer
    -> ADE_Feature_editor_6 [ADE_Feature]
nrg3_CompositeSchedule (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_type xml_buffer, nrg3_type_codeSpace xml_buffer, nrg3_start_time xml_time, nrg3_start_day xml_int64, nrg3_start_month xml_int64, nrg3_start_year xml_int64, nrg3_temporal_extent xml_real64, nrg3_temporal_extent_unit xml_buffer, nrg3_temporal_extent_radix xml_uint64, nrg3_temporal_extent_factor xml_int64, nrg3_schedule_component{}.xlink_href xml_buffer
    -> ADE_Feature_editor_6 [ADE_Feature]

Bookmark: TimeSeries
Junction_18
    -> ADE_Feature_editor_8 [objectclass_name_list]
nrg3_RegularTimeSeries (reader CITYGML_2)
    attributes: citygml_target_uri xml_buffer, citygml_feature_role xml_buffer, citygml_feature_role_attr_name xml_buffer, citygml_feature_role_attr_val xml_buffer, nrg3_acquisition_method xml_buffer, nrg3_acquisition_method_codeSpace xml_buffer, nrg3_interpolation_type xml_char(28), nrg3_source xml_buffer, nrg3_temporal_extent_xlink_href xml_buffer, nrg3_temporal_extent_gml_time_period_frame xml_buffer, nrg3_temporal_extent_gml_time_period_gml_id xml_buffer, nrg3_temporal_extent_gml_time_period_gml_related_time{}.relativePosition xml_char(12), nrg3_temporal_extent_gml_time_period_gml_related_time{}.xlink_href xml_buffer, nrg3_temporal_extent_gml_time_period_gml_related_time{}.gml_time_edge_gml_id xml_buffer, nrg3_temporal_extent_gml_time_period_gml_related_time{}.gml_time_edge_gml_related_time{} xml_xml, nrg3_temporal_extent_gml_time_period_gml_related_time{}.gml_time_edge_gml_related_time{}.relativePosition xml_char(12), nrg3_temporal_extent_gml_time_period_gml_related_time{}.gml_time_edge_gml_related_time{}.xlink_href xml_buffer, nrg3_temporal_extent_gml_time_period_gml_related_time{}.gml_time_edge_gml_complex_xlink_href xml_buffer, nrg3_temporal_extent_gml_time_period_gml_related_time{}.gml_time_edge_gml_start_xlink_href xml_buffer, nrg3_temporal_extent_gml_time_period_gml_related_time{}.gml_time_edge_gml_start_gml_time_node_gml_id xml_buffer, nrg3_temporal_extent_gml_time_period_gml_related_time{}.gml_time_edge_gml_start_gml_time_node_gml_related_time{} xml_xml, nrg3_temporal_extent_gml_time_period_gml_related_time{}.gml_time_edge_gml_start_gml_time_node_gml_related_time{}.relativePosition xml_char(12), nrg3_temporal_extent_gml_time_period_gml_related_time{}.gml_time_edge_gml_start_gml_time_node_gml_related_time{}.xlink_href xml_buffer, nrg3_temporal_extent_gml_time_period_gml_related_time{}.gml_time_edge_gml_start_gml_time_node_gml_complex_xlink_href xml_buffer, nrg3_temporal_extent_gml_time_period_gml_related_time{}.gml_time_edge_gml_start_gml_time_node_gml_previous_edge{}.xlink_href xml_buffer, nrg3_temporal_extent_gml_time_period_gml_related_time{}.gml_time_edge_gml_start_gml_time_node_gml_previous_edge{}.gml_time_edge xml_xml, nrg3_temporal_extent_gml_time_period_gml_related_time{}.gml_time_edge_gml_start_gml_time_node_gml_previous_edge{}.gml_time_edge_gml_id xml_buffer, nrg3_temporal_extent_gml_time_period_gml_related_time{}.gml_time_edge_gml_start_gml_time_node_gml_next_edge{}.xlink_href xml_buffer, nrg3_temporal_extent_gml_time_period_gml_related_time{}.gml_time_edge_gml_start_gml_time_node_gml_next_edge{}.gml_time_edge xml_xml, nrg3_temporal_extent_gml_time_period_gml_related_time{}.gml_time_edge_gml_start_gml_time_node_gml_next_edge{}.gml_time_edge_gml_id xml_buffer,
      nrg3_temporal_extent_gml_time_period_gml_related_time{}.gml_time_edge_gml_start_gml_time_node_gml_position_xlink_href xml_buffer, nrg3_temporal_extent_gml_time_period_gml_related_time{}.gml_time_edge_gml_start_gml_time_node_gml_position_gml_time_instant_frame xml_buffer, nrg3_temporal_extent_gml_time_period_gml_related_time{}.gml_time_edge_gml_start_gml_time_node_gml_position_gml_time_instant_gml_id xml_buffer, nrg3_temporal_extent_gml_time_period_gml_related_time{}.gml_time_edge_gml_start_gml_time_node_gml_position_gml_time_instant_gml_related_time{} xml_xml, nrg3_temporal_extent_gml_time_period_gml_related_time{}.gml_time_edge_gml_start_gml_time_node_gml_position_gml_time_instant_gml_related_time{}.relativePosition xml_char(12), nrg3_temporal_extent_gml_time_period_gml_related_time{}.gml_time_edge_gml_start_gml_time_node_gml_position_gml_time_instant_gml_related_time{}.xlink_href xml_buffer, nrg3_temporal_extent_gml_time_period_gml_related_time{}.gml_time_edge_gml_start_gml_time_node_gml_position_gml_time_instant_gml_time_position xml_buffer, nrg3_temporal_extent_gml_time_period_gml_related_time{}.gml_time_edge_gml_start_gml_time_node_gml_position_gml_time_instant_gml_time_position_frame xml_buffer, nrg3_temporal_extent_gml_time_period_gml_related_time{}.gml_time_edge_gml_start_gml_time_node_gml_position_gml_time_instant_gml_time_position_calendarEraName xml_buffer, nrg3_temporal_extent_gml_time_period_gml_related_time{}.gml_time_edge_gml_start_gml_time_node_gml_position_gml_time_instant_gml_time_position_indeterminatePosition xml_char(7), nrg3_temporal_extent_gml_time_period_gml_related_time{}.gml_time_edge_gml_end_xlink_href xml_buffer, nrg3_temporal_extent_gml_time_period_gml_related_time{}.gml_time_edge_gml_end_gml_time_node_gml_id xml_buffer, nrg3_temporal_extent_gml_time_period_gml_related_time{}.gml_time_edge_gml_end_gml_time_node_gml_related_time{} xml_xml, nrg3_temporal_extent_gml_time_period_gml_related_time{}.gml_time_edge_gml_end_gml_time_node_gml_related_time{}.relativePosition xml_char(12), nrg3_temporal_extent_gml_time_period_gml_related_time{}.gml_time_edge_gml_end_gml_time_node_gml_related_time{}.xlink_href xml_buffer, nrg3_temporal_extent_gml_time_period_gml_related_time{}.gml_time_edge_gml_end_gml_time_node_gml_complex_xlink_href xml_buffer, nrg3_temporal_extent_gml_time_period_gml_related_time{}.gml_time_edge_gml_end_gml_time_node_gml_previous_edge{}.xlink_href xml_buffer, nrg3_temporal_extent_gml_time_period_gml_related_time{}.gml_time_edge_gml_end_gml_time_node_gml_previous_edge{}.gml_time_edge xml_xml, nrg3_temporal_extent_gml_time_period_gml_related_time{}.gml_time_edge_gml_end_gml_time_node_gml_previous_edge{}.gml_time_edge_gml_id xml_buffer, nrg3_temporal_extent_gml_time_period_gml_related_time{}.gml_time_edge_gml_end_gml_time_node_gml_next_edge{}.xlink_href xml_buffer, nrg3_temporal_extent_gml_time_period_gml_related_time{}.gml_time_edge_gml_end_gml_time_node_gml_next_edge{}.gml_time_edge xml_xml, nrg3_temporal_extent_gml_time_period_gml_related_time{}.gml_time_edge_gml_end_gml_time_node_gml_next_edge{}.gml_time_edge_gml_id xml_buffer, nrg3_temporal_extent_gml_time_period_gml_related_time{}.gml_time_edge_gml_end_gml_time_node_gml_position_xlink_href xml_buffer, nrg3_temporal_extent_gml_time_period_gml_related_time{}.gml_time_edge_gml_end_gml_time_node_gml_position_gml_time_instant_frame xml_buffer, nrg3_temporal_extent_gml_time_period_gml_related_time{}.gml_time_edge_gml_end_gml_time_node_gml_position_gml_time_instant_gml_id xml_buffer, nrg3_temporal_extent_gml_time_period_gml_related_time{}.gml_time_edge_gml_end_gml_time_node_gml_position_gml_time_instant_gml_related_time{} xml_xml, nrg3_temporal_extent_gml_time_period_gml_related_time{}.gml_time_edge_gml_end_gml_time_node_gml_position_gml_time_instant_gml_related_time{}.relativePosition xml_char(12), nrg3_temporal_extent_gml_time_period_gml_related_time{}.gml_time_edge_gml_end_gml_time_node_gml_position_gml_time_instant_gml_related_time{}.xlink_href xml_buffer, nrg3_temporal_extent_gml_time_period_gml_related_time{}.gml_time_edge_gml_end_gml_time_node_gml_position_gml_time_instant_gml_time_position xml_buffer, nrg3_temporal_extent_gml_time_period_gml_related_time{}.gml_time_edge_gml_end_gml_time_node_gml_position_gml_time_instant_gml_time_position_frame xml_buffer,
      nrg3_temporal_extent_gml_time_period_gml_related_time{}.gml_time_edge_gml_end_gml_time_node_gml_position_gml_time_instant_gml_time_position_calendarEraName xml_buffer, nrg3_temporal_extent_gml_time_period_gml_related_time{}.gml_time_edge_gml_end_gml_time_node_gml_position_gml_time_instant_gml_time_position_indeterminatePosition xml_char(7), nrg3_temporal_extent_gml_time_period_gml_related_time{}.gml_time_edge_gml_extent_xlink_href xml_buffer, nrg3_temporal_extent_gml_time_period_gml_related_time{}.gml_time_edge_gml_extent_gml_time_period xml_xml, nrg3_temporal_extent_gml_time_period_gml_related_time{}.gml_time_edge_gml_extent_gml_time_period_frame xml_buffer, nrg3_temporal_extent_gml_time_period_gml_related_time{}.gml_time_edge_gml_extent_gml_time_period_gml_id xml_buffer, nrg3_temporal_extent_gml_time_period_gml_related_time{}.gml_time_instant_frame xml_buffer, nrg3_temporal_extent_gml_time_period_gml_related_time{}.gml_time_instant_gml_id xml_buffer, nrg3_temporal_extent_gml_time_period_gml_related_time{}.gml_time_instant_gml_related_time{} xml_xml, nrg3_temporal_extent_gml_time_period_gml_related_time{}.gml_time_instant_gml_related_time{}.relativePosition xml_char(12), nrg3_temporal_extent_gml_time_period_gml_related_time{}.gml_time_instant_gml_related_time{}.xlink_href xml_buffer, nrg3_temporal_extent_gml_time_period_gml_related_time{}.gml_time_instant_gml_time_position xml_buffer, nrg3_temporal_extent_gml_time_period_gml_related_time{}.gml_time_instant_gml_time_position_frame xml_buffer, nrg3_temporal_extent_gml_time_period_gml_related_time{}.gml_time_instant_gml_time_position_calendarEraName xml_buffer, nrg3_temporal_extent_gml_time_period_gml_related_time{}.gml_time_instant_gml_time_position_indeterminatePosition xml_char(7), nrg3_temporal_extent_gml_time_period_gml_related_time{}.gml_time_node_gml_id xml_buffer, nrg3_temporal_extent_gml_time_period_gml_related_time{}.gml_time_node_gml_related_time{} xml_xml, nrg3_temporal_extent_gml_time_period_gml_related_time{}.gml_time_node_gml_related_time{}.relativePosition xml_char(12), nrg3_temporal_extent_gml_time_period_gml_related_time{}.gml_time_node_gml_related_time{}.xlink_href xml_buffer, nrg3_temporal_extent_gml_time_period_gml_related_time{}.gml_time_node_gml_complex_xlink_href xml_buffer, nrg3_temporal_extent_gml_time_period_gml_related_time{}.gml_time_node_gml_previous_edge{}.xlink_href xml_buffer, nrg3_temporal_extent_gml_time_period_gml_related_time{}.gml_time_node_gml_previous_edge{}.gml_time_edge_gml_id xml_buffer, nrg3_temporal_extent_gml_time_period_gml_related_time{}.gml_time_node_gml_previous_edge{}.gml_time_edge_gml_related_time{} xml_xml, nrg3_temporal_extent_gml_time_period_gml_related_time{}.gml_time_node_gml_previous_edge{}.gml_time_edge_gml_related_time{}.relativePosition xml_char(12), nrg3_temporal_extent_gml_time_period_gml_related_time{}.gml_time_node_gml_previous_edge{}.gml_time_edge_gml_related_time{}.xlink_href xml_buffer, nrg3_temporal_extent_gml_time_period_gml_related_time{}.gml_time_node_gml_previous_edge{}.gml_time_edge_gml_complex_xlink_href xml_buffer, nrg3_temporal_extent_gml_time_period_gml_related_time{}.gml_time_node_gml_previous_edge{}.gml_time_edge_gml_start_xlink_href xml_buffer, nrg3_temporal_extent_gml_time_period_gml_related_time{}.gml_time_node_gml_previous_edge{}.gml_time_edge_gml_start_gml_time_node xml_xml, nrg3_temporal_extent_gml_time_period_gml_related_time{}.gml_time_node_gml_previous_edge{}.gml_time_edge_gml_start_gml_time_node_gml_id xml_buffer, nrg3_temporal_extent_gml_time_period_gml_related_time{}.gml_time_node_gml_previous_edge{}.gml_time_edge_gml_end_xlink_href xml_buffer,
      nrg3_temporal_extent_gml_time_period_gml_related_time{}.gml_time_node_gml_previous_edge{}.gml_time_edge_gml_end_gml_time_node xml_xml, nrg3_temporal_extent_gml_time_period_gml_related_time{}.gml_time_node_gml_previous_edge{}.gml_time_edge_gml_end_gml_time_node_gml_id xml_buffer, nrg3_temporal_extent_gml_time_period_gml_related_time{}.gml_time_node_gml_previous_edge{}.gml_time_edge_gml_extent_xlink_href xml_buffer, nrg3_temporal_extent_gml_time_period_gml_related_time{}.gml_time_node_gml_previous_edge{}.gml_time_edge_gml_extent_gml_time_period xml_xml, nrg3_temporal_extent_gml_time_period_gml_related_time{}.gml_time_node_gml_previous_edge{}.gml_time_edge_gml_extent_gml_time_period_frame xml_buffer, nrg3_temporal_extent_gml_time_period_gml_related_time{}.gml_time_node_gml_previous_edge{}.gml_time_edge_gml_extent_gml_time_period_gml_id xml_buffer, nrg3_temporal_extent_gml_time_period_gml_related_time{}.gml_time_node_gml_next_edge{}.xlink_href xml_buffer, nrg3_temporal_extent_gml_time_period_gml_related_time{}.gml_time_node_gml_next_edge{}.gml_time_edge_gml_id xml_buffer, nrg3_temporal_extent_gml_time_period_gml_related_time{}.gml_time_node_gml_next_edge{}.gml_time_edge_gml_related_time{} xml_xml, nrg3_temporal_extent_gml_time_period_gml_related_time{}.gml_time_node_gml_next_edge{}.gml_time_edge_gml_related_time{}.relativePosition xml_char(12), nrg3_temporal_extent_gml_time_period_gml_related_time{}.gml_time_node_gml_next_edge{}.gml_time_edge_gml_related_time{}.xlink_href xml_buffer, nrg3_temporal_extent_gml_time_period_gml_related_time{}.gml_time_node_gml_next_edge{}.gml_time_edge_gml_complex_xlink_href xml_buffer, nrg3_temporal_extent_gml_time_period_gml_related_time{}.gml_time_node_gml_next_edge{}.gml_time_edge_gml_start_xlink_href xml_buffer, nrg3_temporal_extent_gml_time_period_gml_related_time{}.gml_time_node_gml_next_edge{}.gml_time_edge_gml_start_gml_time_node xml_xml, nrg3_temporal_extent_gml_time_period_gml_related_time{}.gml_time_node_gml_next_edge{}.gml_time_edge_gml_start_gml_time_node_gml_id xml_buffer, nrg3_temporal_extent_gml_time_period_gml_related_time{}.gml_time_node_gml_next_edge{}.gml_time_edge_gml_end_xlink_href xml_buffer, nrg3_temporal_extent_gml_time_period_gml_related_time{}.gml_time_node_gml_next_edge{}.gml_time_edge_gml_end_gml_time_node xml_xml, nrg3_temporal_extent_gml_time_period_gml_related_time{}.gml_time_node_gml_next_edge{}.gml_time_edge_gml_end_gml_time_node_gml_id xml_buffer, nrg3_temporal_extent_gml_time_period_gml_related_time{}.gml_time_node_gml_next_edge{}.gml_time_edge_gml_extent_xlink_href xml_buffer, nrg3_temporal_extent_gml_time_period_gml_related_time{}.gml_time_node_gml_next_edge{}.gml_time_edge_gml_extent_gml_time_period xml_xml, nrg3_temporal_extent_gml_time_period_gml_related_time{}.gml_time_node_gml_next_edge{}.gml_time_edge_gml_extent_gml_time_period_frame xml_buffer, nrg3_temporal_extent_gml_time_period_gml_related_time{}.gml_time_node_gml_next_edge{}.gml_time_edge_gml_extent_gml_time_period_gml_id xml_buffer, nrg3_temporal_extent_gml_time_period_gml_related_time{}.gml_time_node_gml_position_xlink_href xml_buffer, nrg3_temporal_extent_gml_time_period_gml_related_time{}.gml_time_node_gml_position_gml_time_instant_frame xml_buffer, nrg3_temporal_extent_gml_time_period_gml_related_time{}.gml_time_node_gml_position_gml_time_instant_gml_id xml_buffer, nrg3_temporal_extent_gml_time_period_gml_related_time{}.gml_time_node_gml_position_gml_time_instant_gml_related_time{} xml_xml, nrg3_temporal_extent_gml_time_period_gml_related_time{}.gml_time_node_gml_position_gml_time_instant_gml_related_time{}.relativePosition xml_char(12), nrg3_temporal_extent_gml_time_period_gml_related_time{}.gml_time_node_gml_position_gml_time_instant_gml_related_time{}.xlink_href xml_buffer, nrg3_temporal_extent_gml_time_period_gml_related_time{}.gml_time_node_gml_position_gml_time_instant_gml_time_position xml_buffer, nrg3_temporal_extent_gml_time_period_gml_related_time{}.gml_time_node_gml_position_gml_time_instant_gml_time_position_frame xml_buffer,
      nrg3_temporal_extent_gml_time_period_gml_related_time{}.gml_time_node_gml_position_gml_time_instant_gml_time_position_calendarEraName xml_buffer, nrg3_temporal_extent_gml_time_period_gml_related_time{}.gml_time_node_gml_position_gml_time_instant_gml_time_position_indeterminatePosition xml_char(7), nrg3_temporal_extent_gml_time_period_gml_related_time{}.gml_time_period xml_xml, nrg3_temporal_extent_gml_time_period_gml_related_time{}.gml_time_period_frame xml_buffer, nrg3_temporal_extent_gml_time_period_gml_related_time{}.gml_time_period_gml_id xml_buffer, nrg3_temporal_extent_gml_time_period_gml_begin_position xml_buffer, nrg3_temporal_extent_gml_time_period_gml_begin_position_frame xml_buffer, nrg3_temporal_extent_gml_time_period_gml_begin_position_calendarEraName xml_buffer, nrg3_temporal_extent_gml_time_period_gml_begin_position_indeterminatePosition xml_char(7), nrg3_temporal_extent_gml_time_period_gml_begin_xlink_href xml_buffer, nrg3_temporal_extent_gml_time_period_gml_begin_gml_time_instant_frame xml_buffer, nrg3_temporal_extent_gml_time_period_gml_begin_gml_time_instant_gml_id xml_buffer, nrg3_temporal_extent_gml_time_period_gml_begin_gml_time_instant_gml_related_time{}.relativePosition xml_char(12), nrg3_temporal_extent_gml_time_period_gml_begin_gml_time_instant_gml_related_time{}.xlink_href xml_buffer, nrg3_temporal_extent_gml_time_period_gml_begin_gml_time_instant_gml_related_time{}.gml_time_edge_gml_id xml_buffer, nrg3_temporal_extent_gml_time_period_gml_begin_gml_time_instant_gml_related_time{}.gml_time_edge_gml_related_time{} xml_xml, nrg3_temporal_extent_gml_time_period_gml_begin_gml_time_instant_gml_related_time{}.gml_time_edge_gml_related_time{}.relativePosition xml_char(12), nrg3_temporal_extent_gml_time_period_gml_begin_gml_time_instant_gml_related_time{}.gml_time_edge_gml_related_time{}.xlink_href xml_buffer, nrg3_temporal_extent_gml_time_period_gml_begin_gml_time_instant_gml_related_time{}.gml_time_edge_gml_complex_xlink_href xml_buffer, nrg3_temporal_extent_gml_time_period_gml_begin_gml_time_instant_gml_related_time{}.gml_time_edge_gml_start_xlink_href xml_buffer, nrg3_temporal_extent_gml_time_period_gml_begin_gml_time_instant_gml_related_time{}.gml_time_edge_gml_start_gml_time_node_gml_id xml_buffer, nrg3_temporal_extent_gml_time_period_gml_begin_gml_time_instant_gml_related_time{}.gml_time_edge_gml_start_gml_time_node_gml_related_time{} xml_xml, nrg3_temporal_extent_gml_time_period_gml_begin_gml_time_instant_gml_related_time{}.gml_time_edge_gml_start_gml_time_node_gml_related_time{}.relativePosition xml_char(12), nrg3_temporal_extent_gml_time_period_gml_begin_gml_time_instant_gml_related_time{}.gml_time_edge_gml_start_gml_time_node_gml_related_time{}.xlink_href xml_buffer, nrg3_temporal_extent_gml_time_period_gml_begin_gml_time_instant_gml_related_time{}.gml_time_edge_gml_start_gml_time_node_gml_complex_xlink_href xml_buffer, nrg3_temporal_extent_gml_time_period_gml_begin_gml_time_instant_gml_related_time{}.gml_time_edge_gml_start_gml_time_node_gml_previous_edge{}.xlink_href xml_buffer, nrg3_temporal_extent_gml_time_period_gml_begin_gml_time_instant_gml_related_time{}.gml_time_edge_gml_start_gml_time_node_gml_previous_edge{}.gml_time_edge xml_xml, nrg3_temporal_extent_gml_time_period_gml_begin_gml_time_instant_gml_related_time{}.gml_time_edge_gml_start_gml_time_node_gml_previous_edge{}.gml_time_edge_gml_id xml_buffer, nrg3_temporal_extent_gml_time_period_gml_begin_gml_time_instant_gml_related_time{}.gml_time_edge_gml_start_gml_time_node_gml_next_edge{}.xlink_href xml_buffer, nrg3_temporal_extent_gml_time_period_gml_begin_gml_time_instant_gml_related_time{}.gml_time_edge_gml_start_gml_time_node_gml_next_edge{}.gml_time_edge xml_xml,
      nrg3_temporal_extent_gml_time_period_gml_begin_gml_time_instant_gml_related_time{}.gml_time_edge_gml_start_gml_time_node_gml_next_edge{}.gml_time_edge_gml_id xml_buffer, nrg3_temporal_extent_gml_time_period_gml_begin_gml_time_instant_gml_related_time{}.gml_time_edge_gml_start_gml_time_node_gml_position_xlink_href xml_buffer, nrg3_temporal_extent_gml_time_period_gml_begin_gml_time_instant_gml_related_time{}.gml_time_edge_gml_start_gml_time_node_gml_position_gml_time_instant xml_xml, nrg3_temporal_extent_gml_time_period_gml_begin_gml_time_instant_gml_related_time{}.gml_time_edge_gml_start_gml_time_node_gml_position_gml_time_instant_frame xml_buffer, nrg3_temporal_extent_gml_time_period_gml_begin_gml_time_instant_gml_related_time{}.gml_time_edge_gml_start_gml_time_node_gml_position_gml_time_instant_gml_id xml_buffer, nrg3_temporal_extent_gml_time_period_gml_begin_gml_time_instant_gml_related_time{}.gml_time_edge_gml_end_xlink_href xml_buffer, nrg3_temporal_extent_gml_time_period_gml_begin_gml_time_instant_gml_related_time{}.gml_time_edge_gml_end_gml_time_node_gml_id xml_buffer, nrg3_temporal_extent_gml_time_period_gml_begin_gml_time_instant_gml_related_time{}.gml_time_edge_gml_end_gml_time_node_gml_related_time{} xml_xml, nrg3_temporal_extent_gml_time_period_gml_begin_gml_time_instant_gml_related_time{}.gml_time_edge_gml_end_gml_time_node_gml_related_time{}.relativePosition xml_char(12), nrg3_temporal_extent_gml_time_period_gml_begin_gml_time_instant_gml_related_time{}.gml_time_edge_gml_end_gml_time_node_gml_related_time{}.xlink_href xml_buffer, nrg3_temporal_extent_gml_time_period_gml_begin_gml_time_instant_gml_related_time{}.gml_time_edge_gml_end_gml_time_node_gml_complex_xlink_href xml_buffer, nrg3_temporal_extent_gml_time_period_gml_begin_gml_time_instant_gml_related_time{}.gml_time_edge_gml_end_gml_time_node_gml_previous_edge{}.xlink_href xml_buffer, nrg3_temporal_extent_gml_time_period_gml_begin_gml_time_instant_gml_related_time{}.gml_time_edge_gml_end_gml_time_node_gml_previous_edge{}.gml_time_edge xml_xml, nrg3_temporal_extent_gml_time_period_gml_begin_gml_time_instant_gml_related_time{}.gml_time_edge_gml_end_gml_time_node_gml_previous_edge{}.gml_time_edge_gml_id xml_buffer, nrg3_temporal_extent_gml_time_period_gml_begin_gml_time_instant_gml_related_time{}.gml_time_edge_gml_end_gml_time_node_gml_next_edge{}.xlink_href xml_buffer, nrg3_temporal_extent_gml_time_period_gml_begin_gml_time_instant_gml_related_time{}.gml_time_edge_gml_end_gml_time_node_gml_next_edge{}.gml_time_edge xml_xml, nrg3_temporal_extent_gml_time_period_gml_begin_gml_time_instant_gml_related_time{}.gml_time_edge_gml_end_gml_time_node_gml_next_edge{}.gml_time_edge_gml_id xml_buffer, nrg3_temporal_extent_gml_time_period_gml_begin_gml_time_instant_gml_related_time{}.gml_time_edge_gml_end_gml_time_node_gml_position_xlink_href xml_buffer, nrg3_temporal_extent_gml_time_period_gml_begin_gml_time_instant_gml_related_time{}.gml_time_edge_gml_end_gml_time_node_gml_position_gml_time_instant xml_xml, nrg3_temporal_extent_gml_time_period_gml_begin_gml_time_instant_gml_related_time{}.gml_time_edge_gml_end_gml_time_node_gml_position_gml_time_instant_frame xml_buffer, nrg3_temporal_extent_gml_time_period_gml_begin_gml_time_instant_gml_related_time{}.gml_time_edge_gml_end_gml_time_node_gml_position_gml_time_instant_gml_id xml_buffer, nrg3_temporal_extent_gml_time_period_gml_begin_gml_time_instant_gml_related_time{}.gml_time_edge_gml_extent_xlink_href xml_buffer, nrg3_temporal_extent_gml_time_period_gml_begin_gml_time_instant_gml_related_time{}.gml_time_edge_gml_extent_gml_time_period xml_xml, nrg3_temporal_extent_gml_time_period_gml_begin_gml_time_instant_gml_related_time{}.gml_time_edge_gml_extent_gml_time_period_frame xml_buffer, nrg3_temporal_extent_gml_time_period_gml_begin_gml_time_instant_gml_related_time{}.gml_time_edge_gml_extent_gml_time_period_gml_id xml_buffer, nrg3_temporal_extent_gml_time_period_gml_begin_gml_time_instant_gml_related_time{}.gml_time_instant xml_xml, nrg3_temporal_extent_gml_time_period_gml_begin_gml_time_instant_gml_related_time{}.gml_time_instant_frame xml_buffer, nrg3_temporal_extent_gml_time_period_gml_begin_gml_time_instant_gml_related_time{}.gml_time_instant_gml_id xml_buffer, nrg3_temporal_extent_gml_time_period_gml_begin_gml_time_instant_gml_related_time{}.gml_time_node_gml_id xml_buffer, nrg3_temporal_extent_gml_time_period_gml_begin_gml_time_instant_gml_related_time{}.gml_time_node_gml_related_time{} xml_xml,
      nrg3_temporal_extent_gml_time_period_gml_begin_gml_time_instant_gml_related_time{}.gml_time_node_gml_related_time{}.relativePosition xml_char(12), nrg3_temporal_extent_gml_time_period_gml_begin_gml_time_instant_gml_related_time{}.gml_time_node_gml_related_time{}.xlink_href xml_buffer, nrg3_temporal_extent_gml_time_period_gml_begin_gml_time_instant_gml_related_time{}.gml_time_node_gml_complex_xlink_href xml_buffer, nrg3_temporal_extent_gml_time_period_gml_begin_gml_time_instant_gml_related_time{}.gml_time_node_gml_previous_edge{}.xlink_href xml_buffer, nrg3_temporal_extent_gml_time_period_gml_begin_gml_time_instant_gml_related_time{}.gml_time_node_gml_previous_edge{}.gml_time_edge_gml_id xml_buffer, nrg3_temporal_extent_gml_time_period_gml_begin_gml_time_instant_gml_related_time{}.gml_time_node_gml_previous_edge{}.gml_time_edge_gml_related_time{} xml_xml, nrg3_temporal_extent_gml_time_period_gml_begin_gml_time_instant_gml_related_time{}.gml_time_node_gml_previous_edge{}.gml_time_edge_gml_related_time{}.relativePosition xml_char(12), nrg3_temporal_extent_gml_time_period_gml_begin_gml_time_instant_gml_related_time{}.gml_time_node_gml_previous_edge{}.gml_time_edge_gml_related_time{}.xlink_href xml_buffer, nrg3_temporal_extent_gml_time_period_gml_begin_gml_time_instant_gml_related_time{}.gml_time_node_gml_previous_edge{}.gml_time_edge_gml_complex_xlink_href xml_buffer, nrg3_temporal_extent_gml_time_period_gml_begin_gml_time_instant_gml_related_time{}.gml_time_node_gml_previous_edge{}.gml_time_edge_gml_start_xlink_href xml_buffer, nrg3_temporal_extent_gml_time_period_gml_begin_gml_time_instant_gml_related_time{}.gml_time_node_gml_previous_edge{}.gml_time_edge_gml_start_gml_time_node xml_xml, nrg3_temporal_extent_gml_time_period_gml_begin_gml_time_instant_gml_related_time{}.gml_time_node_gml_previous_edge{}.gml_time_edge_gml_start_gml_time_node_gml_id xml_buffer, nrg3_temporal_extent_gml_time_period_gml_begin_gml_time_instant_gml_related_time{}.gml_time_node_gml_previous_edge{}.gml_time_edge_gml_end_xlink_href xml_buffer, nrg3_temporal_extent_gml_time_period_gml_begin_gml_time_instant_gml_related_time{}.gml_time_node_gml_previous_edge{}.gml_time_edge_gml_end_gml_time_node xml_xml, nrg3_temporal_extent_gml_time_period_gml_begin_gml_time_instant_gml_related_time{}.gml_time_node_gml_previous_edge{}.gml_time_edge_gml_end_gml_time_node_gml_id xml_buffer, nrg3_temporal_extent_gml_time_period_gml_begin_gml_time_instant_gml_related_time{}.gml_time_node_gml_previous_edge{}.gml_time_edge_gml_extent_xlink_href xml_buffer, nrg3_temporal_extent_gml_time_period_gml_begin_gml_time_instant_gml_related_time{}.gml_time_node_gml_previous_edge{}.gml_time_edge_gml_extent_gml_time_period xml_xml, nrg3_temporal_extent_gml_time_period_gml_begin_gml_time_instant_gml_related_time{}.gml_time_node_gml_previous_edge{}.gml_time_edge_gml_extent_gml_time_period_frame xml_buffer, nrg3_temporal_extent_gml_time_period_gml_begin_gml_time_instant_gml_related_time{}.gml_time_node_gml_previous_edge{}.gml_time_edge_gml_extent_gml_time_period_gml_id xml_buffer, nrg3_temporal_extent_gml_time_period_gml_begin_gml_time_instant_gml_related_time{}.gml_time_node_gml_next_edge{}.xlink_href xml_buffer, nrg3_temporal_extent_gml_time_period_gml_begin_gml_time_instant_gml_related_time{}.gml_time_node_gml_next_edge{}.gml_time_edge_gml_id xml_buffer, nrg3_temporal_extent_gml_time_period_gml_begin_gml_time_instant_gml_related_time{}.gml_time_node_gml_next_edge{}.gml_time_edge_gml_related_time{} xml_xml, nrg3_temporal_extent_gml_time_period_gml_begin_gml_time_instant_gml_related_time{}.gml_time_node_gml_next_edge{}.gml_time_edge_gml_related_time{}.relativePosition xml_char(12), nrg3_temporal_extent_gml_time_period_gml_begin_gml_time_instant_gml_related_time{}.gml_time_node_gml_next_edge{}.gml_time_edge_gml_related_time{}.xlink_href xml_buffer, nrg3_temporal_extent_gml_time_period_gml_begin_gml_time_instant_gml_related_time{}.gml_time_node_gml_next_edge{}.gml_time_edge_gml_complex_xlink_href xml_buffer, nrg3_temporal_extent_gml_time_period_gml_begin_gml_time_instant_gml_related_time{}.gml_time_node_gml_next_edge{}.gml_time_edge_gml_start_xlink_href xml_buffer, nrg3_temporal_extent_gml_time_period_gml_begin_gml_time_instant_gml_related_time{}.gml_time_node_gml_next_edge{}.gml_time_edge_gml_start_gml_time_node xml_xml, nrg3_temporal_extent_gml_time_period_gml_begin_gml_time_instant_gml_related_time{}.gml_time_node_gml_next_edge{}.gml_time_edge_gml_start_gml_time_node_gml_id xml_buffer, nrg3_temporal_extent_gml_time_period_gml_begin_gml_time_instant_gml_related_time{}.gml_time_node_gml_next_edge{}.gml_time_edge_gml_end_xlink_href xml_buffer, nrg3_temporal_extent_gml_time_period_gml_begin_gml_time_instant_gml_related_time{}.gml_time_node_gml_next_edge{}.gml_time_edge_gml_end_gml_time_node xml_xml,
      nrg3_temporal_extent_gml_time_period_gml_begin_gml_time_instant_gml_related_time{}.gml_time_node_gml_next_edge{}.gml_time_edge_gml_end_gml_time_node_gml_id xml_buffer, nrg3_temporal_extent_gml_time_period_gml_begin_gml_time_instant_gml_related_time{}.gml_time_node_gml_next_edge{}.gml_time_edge_gml_extent_xlink_href xml_buffer, nrg3_temporal_extent_gml_time_period_gml_begin_gml_time_instant_gml_related_time{}.gml_time_node_gml_next_edge{}.gml_time_edge_gml_extent_gml_time_period xml_xml, nrg3_temporal_extent_gml_time_period_gml_begin_gml_time_instant_gml_related_time{}.gml_time_node_gml_next_edge{}.gml_time_edge_gml_extent_gml_time_period_frame xml_buffer, nrg3_temporal_extent_gml_time_period_gml_begin_gml_time_instant_gml_related_time{}.gml_time_node_gml_next_edge{}.gml_time_edge_gml_extent_gml_time_period_gml_id xml_buffer, nrg3_temporal_extent_gml_time_period_gml_begin_gml_time_instant_gml_related_time{}.gml_time_node_gml_position_xlink_href xml_buffer, nrg3_temporal_extent_gml_time_period_gml_begin_gml_time_instant_gml_related_time{}.gml_time_node_gml_position_gml_time_instant xml_xml, nrg3_temporal_extent_gml_time_period_gml_begin_gml_time_instant_gml_related_time{}.gml_time_node_gml_position_gml_time_instant_frame xml_buffer, nrg3_temporal_extent_gml_time_period_gml_begin_gml_time_instant_gml_related_time{}.gml_time_node_gml_position_gml_time_instant_gml_id xml_buffer, nrg3_temporal_extent_gml_time_period_gml_begin_gml_time_instant_gml_related_time{}.gml_time_period xml_xml, nrg3_temporal_extent_gml_time_period_gml_begin_gml_time_instant_gml_related_time{}.gml_time_period_frame xml_buffer, nrg3_temporal_extent_gml_time_period_gml_begin_gml_time_instant_gml_related_time{}.gml_time_period_gml_id xml_buffer, nrg3_temporal_extent_gml_time_period_gml_begin_gml_time_instant_gml_time_position xml_buffer, nrg3_temporal_extent_gml_time_period_gml_begin_gml_time_instant_gml_time_position_frame xml_buffer, nrg3_temporal_extent_gml_time_period_gml_begin_gml_time_instant_gml_time_position_calendarEraName xml_buffer, nrg3_temporal_extent_gml_time_period_gml_begin_gml_time_instant_gml_time_position_indeterminatePosition xml_char(7), nrg3_temporal_extent_gml_time_period_gml_end_position xml_buffer, nrg3_temporal_extent_gml_time_period_gml_end_position_frame xml_buffer, nrg3_temporal_extent_gml_time_period_gml_end_position_calendarEraName xml_buffer, nrg3_temporal_extent_gml_time_period_gml_end_position_indeterminatePosition xml_char(7), nrg3_temporal_extent_gml_time_period_gml_end_xlink_href xml_buffer, nrg3_temporal_extent_gml_time_period_gml_end_gml_time_instant_frame xml_buffer, nrg3_temporal_extent_gml_time_period_gml_end_gml_time_instant_gml_id xml_buffer, nrg3_temporal_extent_gml_time_period_gml_end_gml_time_instant_gml_related_time{}.relativePosition xml_char(12), nrg3_temporal_extent_gml_time_period_gml_end_gml_time_instant_gml_related_time{}.xlink_href xml_buffer, nrg3_temporal_extent_gml_time_period_gml_end_gml_time_instant_gml_related_time{}.gml_time_edge_gml_id xml_buffer, nrg3_temporal_extent_gml_time_period_gml_end_gml_time_instant_gml_related_time{}.gml_time_edge_gml_related_time{} xml_xml, nrg3_temporal_extent_gml_time_period_gml_end_gml_time_instant_gml_related_time{}.gml_time_edge_gml_related_time{}.relativePosition xml_char(12), nrg3_temporal_extent_gml_time_period_gml_end_gml_time_instant_gml_related_time{}.gml_time_edge_gml_related_time{}.xlink_href xml_buffer, nrg3_temporal_extent_gml_time_period_gml_end_gml_time_instant_gml_related_time{}.gml_time_edge_gml_complex_xlink_href xml_buffer,
      nrg3_temporal_extent_gml_time_period_gml_end_gml_time_instant_gml_related_time{}.gml_time_edge_gml_start_xlink_href xml_buffer, nrg3_temporal_extent_gml_time_period_gml_end_gml_time_instant_gml_related_time{}.gml_time_edge_gml_start_gml_time_node_gml_id xml_buffer, nrg3_temporal_extent_gml_time_period_gml_end_gml_time_instant_gml_related_time{}.gml_time_edge_gml_start_gml_time_node_gml_related_time{} xml_xml, nrg3_temporal_extent_gml_time_period_gml_end_gml_time_instant_gml_related_time{}.gml_time_edge_gml_start_gml_time_node_gml_related_time{}.relativePosition xml_char(12), nrg3_temporal_extent_gml_time_period_gml_end_gml_time_instant_gml_related_time{}.gml_time_edge_gml_start_gml_time_node_gml_related_time{}.xlink_href xml_buffer, nrg3_temporal_extent_gml_time_period_gml_end_gml_time_instant_gml_related_time{}.gml_time_edge_gml_start_gml_time_node_gml_complex_xlink_href xml_buffer, nrg3_temporal_extent_gml_time_period_gml_end_gml_time_instant_gml_related_time{}.gml_time_edge_gml_start_gml_time_node_gml_previous_edge{}.xlink_href xml_buffer, nrg3_temporal_extent_gml_time_period_gml_end_gml_time_instant_gml_related_time{}.gml_time_edge_gml_start_gml_time_node_gml_previous_edge{}.gml_time_edge xml_xml, nrg3_temporal_extent_gml_time_period_gml_end_gml_time_instant_gml_related_time{}.gml_time_edge_gml_start_gml_time_node_gml_previous_edge{}.gml_time_edge_gml_id xml_buffer, nrg3_temporal_extent_gml_time_period_gml_end_gml_time_instant_gml_related_time{}.gml_time_edge_gml_start_gml_time_node_gml_next_edge{}.xlink_href xml_buffer, nrg3_temporal_extent_gml_time_period_gml_end_gml_time_instant_gml_related_time{}.gml_time_edge_gml_start_gml_time_node_gml_next_edge{}.gml_time_edge xml_xml, nrg3_temporal_extent_gml_time_period_gml_end_gml_time_instant_gml_related_time{}.gml_time_edge_gml_start_gml_time_node_gml_next_edge{}.gml_time_edge_gml_id xml_buffer, nrg3_temporal_extent_gml_time_period_gml_end_gml_time_instant_gml_related_time{}.gml_time_edge_gml_start_gml_time_node_gml_position_xlink_href xml_buffer, nrg3_temporal_extent_gml_time_period_gml_end_gml_time_instant_gml_related_time{}.gml_time_edge_gml_start_gml_time_node_gml_position_gml_time_instant xml_xml, nrg3_temporal_extent_gml_time_period_gml_end_gml_time_instant_gml_related_time{}.gml_time_edge_gml_start_gml_time_node_gml_position_gml_time_instant_frame xml_buffer, nrg3_temporal_extent_gml_time_period_gml_end_gml_time_instant_gml_related_time{}.gml_time_edge_gml_start_gml_time_node_gml_position_gml_time_instant_gml_id xml_buffer, nrg3_temporal_extent_gml_time_period_gml_end_gml_time_instant_gml_related_time{}.gml_time_edge_gml_end_xlink_href xml_buffer, nrg3_temporal_extent_gml_time_period_gml_end_gml_time_instant_gml_related_time{}.gml_time_edge_gml_end_gml_time_node_gml_id xml_buffer, nrg3_temporal_extent_gml_time_period_gml_end_gml_time_instant_gml_related_time{}.gml_time_edge_gml_end_gml_time_node_gml_related_time{} xml_xml, nrg3_temporal_extent_gml_time_period_gml_end_gml_time_instant_gml_related_time{}.gml_time_edge_gml_end_gml_time_node_gml_related_time{}.relativePosition xml_char(12), nrg3_temporal_extent_gml_time_period_gml_end_gml_time_instant_gml_related_time{}.gml_time_edge_gml_end_gml_time_node_gml_related_time{}.xlink_href xml_buffer, nrg3_temporal_extent_gml_time_period_gml_end_gml_time_instant_gml_related_time{}.gml_time_edge_gml_end_gml_time_node_gml_complex_xlink_href xml_buffer, nrg3_temporal_extent_gml_time_period_gml_end_gml_time_instant_gml_related_time{}.gml_time_edge_gml_end_gml_time_node_gml_previous_edge{}.xlink_href xml_buffer, nrg3_temporal_extent_gml_time_period_gml_end_gml_time_instant_gml_related_time{}.gml_time_edge_gml_end_gml_time_node_gml_previous_edge{}.gml_time_edge xml_xml, nrg3_temporal_extent_gml_time_period_gml_end_gml_time_instant_gml_related_time{}.gml_time_edge_gml_end_gml_time_node_gml_previous_edge{}.gml_time_edge_gml_id xml_buffer, nrg3_temporal_extent_gml_time_period_gml_end_gml_time_instant_gml_related_time{}.gml_time_edge_gml_end_gml_time_node_gml_next_edge{}.xlink_href xml_buffer, nrg3_temporal_extent_gml_time_period_gml_end_gml_time_instant_gml_related_time{}.gml_time_edge_gml_end_gml_time_node_gml_next_edge{}.gml_time_edge xml_xml, nrg3_temporal_extent_gml_time_period_gml_end_gml_time_instant_gml_related_time{}.gml_time_edge_gml_end_gml_time_node_gml_next_edge{}.gml_time_edge_gml_id xml_buffer, nrg3_temporal_extent_gml_time_period_gml_end_gml_time_instant_gml_related_time{}.gml_time_edge_gml_end_gml_time_node_gml_position_xlink_href xml_buffer, nrg3_temporal_extent_gml_time_period_gml_end_gml_time_instant_gml_related_time{}.gml_time_edge_gml_end_gml_time_node_gml_position_gml_time_instant xml_xml,
      nrg3_temporal_extent_gml_time_period_gml_end_gml_time_instant_gml_related_time{}.gml_time_edge_gml_end_gml_time_node_gml_position_gml_time_instant_frame xml_buffer, nrg3_temporal_extent_gml_time_period_gml_end_gml_time_instant_gml_related_time{}.gml_time_edge_gml_end_gml_time_node_gml_position_gml_time_instant_gml_id xml_buffer, nrg3_temporal_extent_gml_time_period_gml_end_gml_time_instant_gml_related_time{}.gml_time_edge_gml_extent_xlink_href xml_buffer, nrg3_temporal_extent_gml_time_period_gml_end_gml_time_instant_gml_related_time{}.gml_time_edge_gml_extent_gml_time_period xml_xml, nrg3_temporal_extent_gml_time_period_gml_end_gml_time_instant_gml_related_time{}.gml_time_edge_gml_extent_gml_time_period_frame xml_buffer, nrg3_temporal_extent_gml_time_period_gml_end_gml_time_instant_gml_related_time{}.gml_time_edge_gml_extent_gml_time_period_gml_id xml_buffer, nrg3_temporal_extent_gml_time_period_gml_end_gml_time_instant_gml_related_time{}.gml_time_instant xml_xml, nrg3_temporal_extent_gml_time_period_gml_end_gml_time_instant_gml_related_time{}.gml_time_instant_frame xml_buffer, nrg3_temporal_extent_gml_time_period_gml_end_gml_time_instant_gml_related_time{}.gml_time_instant_gml_id xml_buffer, nrg3_temporal_extent_gml_time_period_gml_end_gml_time_instant_gml_related_time{}.gml_time_node_gml_id xml_buffer, nrg3_temporal_extent_gml_time_period_gml_end_gml_time_instant_gml_related_time{}.gml_time_node_gml_related_time{} xml_xml, nrg3_temporal_extent_gml_time_period_gml_end_gml_time_instant_gml_related_time{}.gml_time_node_gml_related_time{}.relativePosition xml_char(12), nrg3_temporal_extent_gml_time_period_gml_end_gml_time_instant_gml_related_time{}.gml_time_node_gml_related_time{}.xlink_href xml_buffer, nrg3_temporal_extent_gml_time_period_gml_end_gml_time_instant_gml_related_time{}.gml_time_node_gml_complex_xlink_href xml_buffer, nrg3_temporal_extent_gml_time_period_gml_end_gml_time_instant_gml_related_time{}.gml_time_node_gml_previous_edge{}.xlink_href xml_buffer, nrg3_temporal_extent_gml_time_period_gml_end_gml_time_instant_gml_related_time{}.gml_time_node_gml_previous_edge{}.gml_time_edge_gml_id xml_buffer, nrg3_temporal_extent_gml_time_period_gml_end_gml_time_instant_gml_related_time{}.gml_time_node_gml_previous_edge{}.gml_time_edge_gml_related_time{} xml_xml, nrg3_temporal_extent_gml_time_period_gml_end_gml_time_instant_gml_related_time{}.gml_time_node_gml_previous_edge{}.gml_time_edge_gml_related_time{}.relativePosition xml_char(12), nrg3_temporal_extent_gml_time_period_gml_end_gml_time_instant_gml_related_time{}.gml_time_node_gml_previous_edge{}.gml_time_edge_gml_related_time{}.xlink_href xml_buffer, nrg3_temporal_extent_gml_time_period_gml_end_gml_time_instant_gml_related_time{}.gml_time_node_gml_previous_edge{}.gml_time_edge_gml_complex_xlink_href xml_buffer, nrg3_temporal_extent_gml_time_period_gml_end_gml_time_instant_gml_related_time{}.gml_time_node_gml_previous_edge{}.gml_time_edge_gml_start_xlink_href xml_buffer, nrg3_temporal_extent_gml_time_period_gml_end_gml_time_instant_gml_related_time{}.gml_time_node_gml_previous_edge{}.gml_time_edge_gml_start_gml_time_node xml_xml, nrg3_temporal_extent_gml_time_period_gml_end_gml_time_instant_gml_related_time{}.gml_time_node_gml_previous_edge{}.gml_time_edge_gml_start_gml_time_node_gml_id xml_buffer, nrg3_temporal_extent_gml_time_period_gml_end_gml_time_instant_gml_related_time{}.gml_time_node_gml_previous_edge{}.gml_time_edge_gml_end_xlink_href xml_buffer, nrg3_temporal_extent_gml_time_period_gml_end_gml_time_instant_gml_related_time{}.gml_time_node_gml_previous_edge{}.gml_time_edge_gml_end_gml_time_node xml_xml, nrg3_temporal_extent_gml_time_period_gml_end_gml_time_instant_gml_related_time{}.gml_time_node_gml_previous_edge{}.gml_time_edge_gml_end_gml_time_node_gml_id xml_buffer, nrg3_temporal_extent_gml_time_period_gml_end_gml_time_instant_gml_related_time{}.gml_time_node_gml_previous_edge{}.gml_time_edge_gml_extent_xlink_href xml_buffer, nrg3_temporal_extent_gml_time_period_gml_end_gml_time_instant_gml_related_time{}.gml_time_node_gml_previous_edge{}.gml_time_edge_gml_extent_gml_time_period xml_xml, nrg3_temporal_extent_gml_time_period_gml_end_gml_time_instant_gml_related_time{}.gml_time_node_gml_previous_edge{}.gml_time_edge_gml_extent_gml_time_period_frame xml_buffer, nrg3_temporal_extent_gml_time_period_gml_end_gml_time_instant_gml_related_time{}.gml_time_node_gml_previous_edge{}.gml_time_edge_gml_extent_gml_time_period_gml_id xml_buffer,
      nrg3_temporal_extent_gml_time_period_gml_end_gml_time_instant_gml_related_time{}.gml_time_node_gml_next_edge{}.xlink_href xml_buffer, nrg3_temporal_extent_gml_time_period_gml_end_gml_time_instant_gml_related_time{}.gml_time_node_gml_next_edge{}.gml_time_edge_gml_id xml_buffer, gml_description xml_buffer, gml_name xml_buffer, nrg3_temporal_extent_gml_time_period_gml_end_gml_time_instant_gml_related_time{}.gml_time_node_gml_next_edge{}.gml_time_edge_gml_related_time{} xml_xml, nrg3_temporal_extent_gml_time_period_gml_end_gml_time_instant_gml_related_time{}.gml_time_node_gml_next_edge{}.gml_time_edge_gml_related_time{}.relativePosition xml_char(12), nrg3_temporal_extent_gml_time_period_gml_end_gml_time_instant_gml_related_time{}.gml_time_node_gml_next_edge{}.gml_time_edge_gml_related_time{}.xlink_href xml_buffer, nrg3_temporal_extent_gml_time_period_gml_end_gml_time_instant_gml_related_time{}.gml_time_node_gml_next_edge{}.gml_time_edge_gml_complex_xlink_href xml_buffer, nrg3_temporal_extent_gml_time_period_gml_end_gml_time_instant_gml_related_time{}.gml_time_node_gml_next_edge{}.gml_time_edge_gml_start_xlink_href xml_buffer, nrg3_temporal_extent_gml_time_period_gml_end_gml_time_instant_gml_related_time{}.gml_time_node_gml_next_edge{}.gml_time_edge_gml_start_gml_time_node xml_xml, nrg3_temporal_extent_gml_time_period_gml_end_gml_time_instant_gml_related_time{}.gml_time_node_gml_next_edge{}.gml_time_edge_gml_start_gml_time_node_gml_id xml_buffer, nrg3_temporal_extent_gml_time_period_gml_end_gml_time_instant_gml_related_time{}.gml_time_node_gml_next_edge{}.gml_time_edge_gml_end_xlink_href xml_buffer, nrg3_temporal_extent_gml_time_period_gml_end_gml_time_instant_gml_related_time{}.gml_time_node_gml_next_edge{}.gml_time_edge_gml_end_gml_time_node xml_xml, nrg3_temporal_extent_gml_time_period_gml_end_gml_time_instant_gml_related_time{}.gml_time_node_gml_next_edge{}.gml_time_edge_gml_end_gml_time_node_gml_id xml_buffer, nrg3_temporal_extent_gml_time_period_gml_end_gml_time_instant_gml_related_time{}.gml_time_node_gml_next_edge{}.gml_time_edge_gml_extent_xlink_href xml_buffer, nrg3_temporal_extent_gml_time_period_gml_end_gml_time_instant_gml_related_time{}.gml_time_node_gml_next_edge{}.gml_time_edge_gml_extent_gml_time_period xml_xml, nrg3_temporal_extent_gml_time_period_gml_end_gml_time_instant_gml_related_time{}.gml_time_node_gml_next_edge{}.gml_time_edge_gml_extent_gml_time_period_frame xml_buffer, nrg3_temporal_extent_gml_time_period_gml_end_gml_time_instant_gml_related_time{}.gml_time_node_gml_next_edge{}.gml_time_edge_gml_extent_gml_time_period_gml_id xml_buffer, nrg3_temporal_extent_gml_time_period_gml_end_gml_time_instant_gml_related_time{}.gml_time_node_gml_position_xlink_href xml_buffer, nrg3_temporal_extent_gml_time_period_gml_end_gml_time_instant_gml_related_time{}.gml_time_node_gml_position_gml_time_instant xml_xml, nrg3_temporal_extent_gml_time_period_gml_end_gml_time_instant_gml_related_time{}.gml_time_node_gml_position_gml_time_instant_frame xml_buffer, nrg3_temporal_extent_gml_time_period_gml_end_gml_time_instant_gml_related_time{}.gml_time_node_gml_position_gml_time_instant_gml_id xml_buffer, nrg3_temporal_extent_gml_time_period_gml_end_gml_time_instant_gml_related_time{}.gml_time_period xml_xml, nrg3_temporal_extent_gml_time_period_gml_end_gml_time_instant_gml_related_time{}.gml_time_period_frame xml_buffer, nrg3_temporal_extent_gml_time_period_gml_end_gml_time_instant_gml_related_time{}.gml_time_period_gml_id xml_buffer, nrg3_temporal_extent_gml_time_period_gml_end_gml_time_instant_gml_time_position xml_buffer, nrg3_temporal_extent_gml_time_period_gml_end_gml_time_instant_gml_time_position_frame xml_buffer, nrg3_temporal_extent_gml_time_period_gml_end_gml_time_instant_gml_time_position_calendarEraName xml_buffer, nrg3_temporal_extent_gml_time_period_gml_end_gml_time_instant_gml_time_position_indeterminatePosition xml_char(7), nrg3_temporal_extent_gml_time_period_gml_duration xml_buffer,
      nrg3_temporal_extent_gml_time_period_gml_time_interval xml_real64, nrg3_temporal_extent_gml_time_period_gml_time_interval_unit xml_buffer, nrg3_temporal_extent_gml_time_period_gml_time_interval_radix xml_uint64, nrg3_temporal_extent_gml_time_period_gml_time_interval_factor xml_int64, nrg3_time_interval xml_real64, nrg3_time_interval_unit xml_buffer, nrg3_time_interval_radix xml_uint64, nrg3_time_interval_factor xml_int64, nrg3_values_list xml_buffer, nrg3_values_list_units xml_buffer
    -> Junction_49
nrg3_RegularTimeSeriesFile (reader CITYGML_2)
    attributes: citygml_target_uri xml_buffer, citygml_feature_role xml_buffer, citygml_feature_role_attr_name xml_buffer, citygml_feature_role_attr_val xml_buffer, nrg3_acquisition_method xml_buffer, nrg3_acquisition_method_codeSpace xml_buffer, nrg3_interpolation_type xml_char(28), nrg3_source xml_buffer, nrg3_uom_units xml_buffer, nrg3_file_uri xml_buffer, nrg3_temporal_extent_xlink_href xml_buffer, nrg3_temporal_extent_gml_time_period_frame xml_buffer, nrg3_temporal_extent_gml_time_period_gml_id xml_buffer, nrg3_temporal_extent_gml_time_period_gml_related_time{}.relativePosition xml_char(12), nrg3_temporal_extent_gml_time_period_gml_related_time{}.xlink_href xml_buffer, nrg3_temporal_extent_gml_time_period_gml_related_time{}.gml_time_edge_gml_id xml_buffer, nrg3_temporal_extent_gml_time_period_gml_related_time{}.gml_time_edge_gml_related_time{} xml_xml, nrg3_temporal_extent_gml_time_period_gml_related_time{}.gml_time_edge_gml_related_time{}.relativePosition xml_char(12), nrg3_temporal_extent_gml_time_period_gml_related_time{}.gml_time_edge_gml_related_time{}.xlink_href xml_buffer, nrg3_temporal_extent_gml_time_period_gml_related_time{}.gml_time_edge_gml_complex_xlink_href xml_buffer, nrg3_temporal_extent_gml_time_period_gml_related_time{}.gml_time_edge_gml_start_xlink_href xml_buffer, nrg3_temporal_extent_gml_time_period_gml_related_time{}.gml_time_edge_gml_start_gml_time_node_gml_id xml_buffer, nrg3_temporal_extent_gml_time_period_gml_related_time{}.gml_time_edge_gml_start_gml_time_node_gml_related_time{} xml_xml, nrg3_temporal_extent_gml_time_period_gml_related_time{}.gml_time_edge_gml_start_gml_time_node_gml_related_time{}.relativePosition xml_char(12), nrg3_temporal_extent_gml_time_period_gml_related_time{}.gml_time_edge_gml_start_gml_time_node_gml_related_time{}.xlink_href xml_buffer, nrg3_temporal_extent_gml_time_period_gml_related_time{}.gml_time_edge_gml_start_gml_time_node_gml_complex_xlink_href xml_buffer, nrg3_temporal_extent_gml_time_period_gml_related_time{}.gml_time_edge_gml_start_gml_time_node_gml_previous_edge{}.xlink_href xml_buffer, nrg3_temporal_extent_gml_time_period_gml_related_time{}.gml_time_edge_gml_start_gml_time_node_gml_previous_edge{}.gml_time_edge xml_xml, nrg3_temporal_extent_gml_time_period_gml_related_time{}.gml_time_edge_gml_start_gml_time_node_gml_previous_edge{}.gml_time_edge_gml_id xml_buffer, nrg3_temporal_extent_gml_time_period_gml_related_time{}.gml_time_edge_gml_start_gml_time_node_gml_next_edge{}.xlink_href xml_buffer,
      nrg3_temporal_extent_gml_time_period_gml_related_time{}.gml_time_edge_gml_start_gml_time_node_gml_next_edge{}.gml_time_edge xml_xml, nrg3_temporal_extent_gml_time_period_gml_related_time{}.gml_time_edge_gml_start_gml_time_node_gml_next_edge{}.gml_time_edge_gml_id xml_buffer, nrg3_temporal_extent_gml_time_period_gml_related_time{}.gml_time_edge_gml_start_gml_time_node_gml_position_xlink_href xml_buffer, nrg3_temporal_extent_gml_time_period_gml_related_time{}.gml_time_edge_gml_start_gml_time_node_gml_position_gml_time_instant_frame xml_buffer, nrg3_temporal_extent_gml_time_period_gml_related_time{}.gml_time_edge_gml_start_gml_time_node_gml_position_gml_time_instant_gml_id xml_buffer, nrg3_temporal_extent_gml_time_period_gml_related_time{}.gml_time_edge_gml_start_gml_time_node_gml_position_gml_time_instant_gml_related_time{} xml_xml, nrg3_temporal_extent_gml_time_period_gml_related_time{}.gml_time_edge_gml_start_gml_time_node_gml_position_gml_time_instant_gml_related_time{}.relativePosition xml_char(12), nrg3_temporal_extent_gml_time_period_gml_related_time{}.gml_time_edge_gml_start_gml_time_node_gml_position_gml_time_instant_gml_related_time{}.xlink_href xml_buffer, nrg3_temporal_extent_gml_time_period_gml_related_time{}.gml_time_edge_gml_start_gml_time_node_gml_position_gml_time_instant_gml_time_position xml_buffer, nrg3_temporal_extent_gml_time_period_gml_related_time{}.gml_time_edge_gml_start_gml_time_node_gml_position_gml_time_instant_gml_time_position_frame xml_buffer, nrg3_temporal_extent_gml_time_period_gml_related_time{}.gml_time_edge_gml_start_gml_time_node_gml_position_gml_time_instant_gml_time_position_calendarEraName xml_buffer, nrg3_temporal_extent_gml_time_period_gml_related_time{}.gml_time_edge_gml_start_gml_time_node_gml_position_gml_time_instant_gml_time_position_indeterminatePosition xml_char(7), nrg3_temporal_extent_gml_time_period_gml_related_time{}.gml_time_edge_gml_end_xlink_href xml_buffer, nrg3_temporal_extent_gml_time_period_gml_related_time{}.gml_time_edge_gml_end_gml_time_node_gml_id xml_buffer, nrg3_temporal_extent_gml_time_period_gml_related_time{}.gml_time_edge_gml_end_gml_time_node_gml_related_time{} xml_xml, nrg3_temporal_extent_gml_time_period_gml_related_time{}.gml_time_edge_gml_end_gml_time_node_gml_related_time{}.relativePosition xml_char(12), nrg3_temporal_extent_gml_time_period_gml_related_time{}.gml_time_edge_gml_end_gml_time_node_gml_related_time{}.xlink_href xml_buffer, nrg3_temporal_extent_gml_time_period_gml_related_time{}.gml_time_edge_gml_end_gml_time_node_gml_complex_xlink_href xml_buffer, nrg3_temporal_extent_gml_time_period_gml_related_time{}.gml_time_edge_gml_end_gml_time_node_gml_previous_edge{}.xlink_href xml_buffer, nrg3_temporal_extent_gml_time_period_gml_related_time{}.gml_time_edge_gml_end_gml_time_node_gml_previous_edge{}.gml_time_edge xml_xml, nrg3_temporal_extent_gml_time_period_gml_related_time{}.gml_time_edge_gml_end_gml_time_node_gml_previous_edge{}.gml_time_edge_gml_id xml_buffer, nrg3_temporal_extent_gml_time_period_gml_related_time{}.gml_time_edge_gml_end_gml_time_node_gml_next_edge{}.xlink_href xml_buffer, nrg3_temporal_extent_gml_time_period_gml_related_time{}.gml_time_edge_gml_end_gml_time_node_gml_next_edge{}.gml_time_edge xml_xml, nrg3_temporal_extent_gml_time_period_gml_related_time{}.gml_time_edge_gml_end_gml_time_node_gml_next_edge{}.gml_time_edge_gml_id xml_buffer, nrg3_temporal_extent_gml_time_period_gml_related_time{}.gml_time_edge_gml_end_gml_time_node_gml_position_xlink_href xml_buffer, nrg3_temporal_extent_gml_time_period_gml_related_time{}.gml_time_edge_gml_end_gml_time_node_gml_position_gml_time_instant_frame xml_buffer, nrg3_temporal_extent_gml_time_period_gml_related_time{}.gml_time_edge_gml_end_gml_time_node_gml_position_gml_time_instant_gml_id xml_buffer, nrg3_temporal_extent_gml_time_period_gml_related_time{}.gml_time_edge_gml_end_gml_time_node_gml_position_gml_time_instant_gml_related_time{} xml_xml, nrg3_temporal_extent_gml_time_period_gml_related_time{}.gml_time_edge_gml_end_gml_time_node_gml_position_gml_time_instant_gml_related_time{}.relativePosition xml_char(12), nrg3_temporal_extent_gml_time_period_gml_related_time{}.gml_time_edge_gml_end_gml_time_node_gml_position_gml_time_instant_gml_related_time{}.xlink_href xml_buffer,
      nrg3_temporal_extent_gml_time_period_gml_related_time{}.gml_time_edge_gml_end_gml_time_node_gml_position_gml_time_instant_gml_time_position xml_buffer, nrg3_temporal_extent_gml_time_period_gml_related_time{}.gml_time_edge_gml_end_gml_time_node_gml_position_gml_time_instant_gml_time_position_frame xml_buffer, nrg3_temporal_extent_gml_time_period_gml_related_time{}.gml_time_edge_gml_end_gml_time_node_gml_position_gml_time_instant_gml_time_position_calendarEraName xml_buffer, nrg3_temporal_extent_gml_time_period_gml_related_time{}.gml_time_edge_gml_end_gml_time_node_gml_position_gml_time_instant_gml_time_position_indeterminatePosition xml_char(7), nrg3_temporal_extent_gml_time_period_gml_related_time{}.gml_time_edge_gml_extent_xlink_href xml_buffer, nrg3_temporal_extent_gml_time_period_gml_related_time{}.gml_time_edge_gml_extent_gml_time_period xml_xml, nrg3_temporal_extent_gml_time_period_gml_related_time{}.gml_time_edge_gml_extent_gml_time_period_frame xml_buffer, nrg3_temporal_extent_gml_time_period_gml_related_time{}.gml_time_edge_gml_extent_gml_time_period_gml_id xml_buffer, nrg3_temporal_extent_gml_time_period_gml_related_time{}.gml_time_instant_frame xml_buffer, nrg3_temporal_extent_gml_time_period_gml_related_time{}.gml_time_instant_gml_id xml_buffer, nrg3_temporal_extent_gml_time_period_gml_related_time{}.gml_time_instant_gml_related_time{} xml_xml, nrg3_temporal_extent_gml_time_period_gml_related_time{}.gml_time_instant_gml_related_time{}.relativePosition xml_char(12), nrg3_temporal_extent_gml_time_period_gml_related_time{}.gml_time_instant_gml_related_time{}.xlink_href xml_buffer, nrg3_temporal_extent_gml_time_period_gml_related_time{}.gml_time_instant_gml_time_position xml_buffer, nrg3_temporal_extent_gml_time_period_gml_related_time{}.gml_time_instant_gml_time_position_frame xml_buffer, nrg3_temporal_extent_gml_time_period_gml_related_time{}.gml_time_instant_gml_time_position_calendarEraName xml_buffer, nrg3_temporal_extent_gml_time_period_gml_related_time{}.gml_time_instant_gml_time_position_indeterminatePosition xml_char(7), nrg3_temporal_extent_gml_time_period_gml_related_time{}.gml_time_node_gml_id xml_buffer, nrg3_temporal_extent_gml_time_period_gml_related_time{}.gml_time_node_gml_related_time{} xml_xml, nrg3_temporal_extent_gml_time_period_gml_related_time{}.gml_time_node_gml_related_time{}.relativePosition xml_char(12), nrg3_temporal_extent_gml_time_period_gml_related_time{}.gml_time_node_gml_related_time{}.xlink_href xml_buffer, nrg3_temporal_extent_gml_time_period_gml_related_time{}.gml_time_node_gml_complex_xlink_href xml_buffer, nrg3_temporal_extent_gml_time_period_gml_related_time{}.gml_time_node_gml_previous_edge{}.xlink_href xml_buffer, nrg3_temporal_extent_gml_time_period_gml_related_time{}.gml_time_node_gml_previous_edge{}.gml_time_edge_gml_id xml_buffer, nrg3_temporal_extent_gml_time_period_gml_related_time{}.gml_time_node_gml_previous_edge{}.gml_time_edge_gml_related_time{} xml_xml, nrg3_temporal_extent_gml_time_period_gml_related_time{}.gml_time_node_gml_previous_edge{}.gml_time_edge_gml_related_time{}.relativePosition xml_char(12), nrg3_temporal_extent_gml_time_period_gml_related_time{}.gml_time_node_gml_previous_edge{}.gml_time_edge_gml_related_time{}.xlink_href xml_buffer, nrg3_temporal_extent_gml_time_period_gml_related_time{}.gml_time_node_gml_previous_edge{}.gml_time_edge_gml_complex_xlink_href xml_buffer, nrg3_temporal_extent_gml_time_period_gml_related_time{}.gml_time_node_gml_previous_edge{}.gml_time_edge_gml_start_xlink_href xml_buffer, nrg3_temporal_extent_gml_time_period_gml_related_time{}.gml_time_node_gml_previous_edge{}.gml_time_edge_gml_start_gml_time_node xml_xml,
      nrg3_temporal_extent_gml_time_period_gml_related_time{}.gml_time_node_gml_previous_edge{}.gml_time_edge_gml_start_gml_time_node_gml_id xml_buffer, nrg3_temporal_extent_gml_time_period_gml_related_time{}.gml_time_node_gml_previous_edge{}.gml_time_edge_gml_end_xlink_href xml_buffer, nrg3_temporal_extent_gml_time_period_gml_related_time{}.gml_time_node_gml_previous_edge{}.gml_time_edge_gml_end_gml_time_node xml_xml, nrg3_temporal_extent_gml_time_period_gml_related_time{}.gml_time_node_gml_previous_edge{}.gml_time_edge_gml_end_gml_time_node_gml_id xml_buffer, nrg3_temporal_extent_gml_time_period_gml_related_time{}.gml_time_node_gml_previous_edge{}.gml_time_edge_gml_extent_xlink_href xml_buffer, nrg3_temporal_extent_gml_time_period_gml_related_time{}.gml_time_node_gml_previous_edge{}.gml_time_edge_gml_extent_gml_time_period xml_xml, nrg3_temporal_extent_gml_time_period_gml_related_time{}.gml_time_node_gml_previous_edge{}.gml_time_edge_gml_extent_gml_time_period_frame xml_buffer, nrg3_temporal_extent_gml_time_period_gml_related_time{}.gml_time_node_gml_previous_edge{}.gml_time_edge_gml_extent_gml_time_period_gml_id xml_buffer, nrg3_temporal_extent_gml_time_period_gml_related_time{}.gml_time_node_gml_next_edge{}.xlink_href xml_buffer, nrg3_temporal_extent_gml_time_period_gml_related_time{}.gml_time_node_gml_next_edge{}.gml_time_edge_gml_id xml_buffer, nrg3_temporal_extent_gml_time_period_gml_related_time{}.gml_time_node_gml_next_edge{}.gml_time_edge_gml_related_time{} xml_xml, nrg3_temporal_extent_gml_time_period_gml_related_time{}.gml_time_node_gml_next_edge{}.gml_time_edge_gml_related_time{}.relativePosition xml_char(12), nrg3_temporal_extent_gml_time_period_gml_related_time{}.gml_time_node_gml_next_edge{}.gml_time_edge_gml_related_time{}.xlink_href xml_buffer, nrg3_temporal_extent_gml_time_period_gml_related_time{}.gml_time_node_gml_next_edge{}.gml_time_edge_gml_complex_xlink_href xml_buffer, nrg3_temporal_extent_gml_time_period_gml_related_time{}.gml_time_node_gml_next_edge{}.gml_time_edge_gml_start_xlink_href xml_buffer, nrg3_temporal_extent_gml_time_period_gml_related_time{}.gml_time_node_gml_next_edge{}.gml_time_edge_gml_start_gml_time_node xml_xml, nrg3_temporal_extent_gml_time_period_gml_related_time{}.gml_time_node_gml_next_edge{}.gml_time_edge_gml_start_gml_time_node_gml_id xml_buffer, nrg3_temporal_extent_gml_time_period_gml_related_time{}.gml_time_node_gml_next_edge{}.gml_time_edge_gml_end_xlink_href xml_buffer, nrg3_temporal_extent_gml_time_period_gml_related_time{}.gml_time_node_gml_next_edge{}.gml_time_edge_gml_end_gml_time_node xml_xml, nrg3_temporal_extent_gml_time_period_gml_related_time{}.gml_time_node_gml_next_edge{}.gml_time_edge_gml_end_gml_time_node_gml_id xml_buffer, nrg3_temporal_extent_gml_time_period_gml_related_time{}.gml_time_node_gml_next_edge{}.gml_time_edge_gml_extent_xlink_href xml_buffer, nrg3_temporal_extent_gml_time_period_gml_related_time{}.gml_time_node_gml_next_edge{}.gml_time_edge_gml_extent_gml_time_period xml_xml, nrg3_temporal_extent_gml_time_period_gml_related_time{}.gml_time_node_gml_next_edge{}.gml_time_edge_gml_extent_gml_time_period_frame xml_buffer, nrg3_temporal_extent_gml_time_period_gml_related_time{}.gml_time_node_gml_next_edge{}.gml_time_edge_gml_extent_gml_time_period_gml_id xml_buffer, nrg3_temporal_extent_gml_time_period_gml_related_time{}.gml_time_node_gml_position_xlink_href xml_buffer, nrg3_temporal_extent_gml_time_period_gml_related_time{}.gml_time_node_gml_position_gml_time_instant_frame xml_buffer, nrg3_temporal_extent_gml_time_period_gml_related_time{}.gml_time_node_gml_position_gml_time_instant_gml_id xml_buffer, nrg3_temporal_extent_gml_time_period_gml_related_time{}.gml_time_node_gml_position_gml_time_instant_gml_related_time{} xml_xml, nrg3_temporal_extent_gml_time_period_gml_related_time{}.gml_time_node_gml_position_gml_time_instant_gml_related_time{}.relativePosition xml_char(12), nrg3_temporal_extent_gml_time_period_gml_related_time{}.gml_time_node_gml_position_gml_time_instant_gml_related_time{}.xlink_href xml_buffer,
      nrg3_temporal_extent_gml_time_period_gml_related_time{}.gml_time_node_gml_position_gml_time_instant_gml_time_position xml_buffer, nrg3_temporal_extent_gml_time_period_gml_related_time{}.gml_time_node_gml_position_gml_time_instant_gml_time_position_frame xml_buffer, nrg3_temporal_extent_gml_time_period_gml_related_time{}.gml_time_node_gml_position_gml_time_instant_gml_time_position_calendarEraName xml_buffer, nrg3_temporal_extent_gml_time_period_gml_related_time{}.gml_time_node_gml_position_gml_time_instant_gml_time_position_indeterminatePosition xml_char(7), nrg3_temporal_extent_gml_time_period_gml_related_time{}.gml_time_period xml_xml, nrg3_temporal_extent_gml_time_period_gml_related_time{}.gml_time_period_frame xml_buffer, nrg3_temporal_extent_gml_time_period_gml_related_time{}.gml_time_period_gml_id xml_buffer, nrg3_temporal_extent_gml_time_period_gml_begin_position xml_buffer, nrg3_temporal_extent_gml_time_period_gml_begin_position_frame xml_buffer, nrg3_temporal_extent_gml_time_period_gml_begin_position_calendarEraName xml_buffer, nrg3_temporal_extent_gml_time_period_gml_begin_position_indeterminatePosition xml_char(7), nrg3_temporal_extent_gml_time_period_gml_begin_xlink_href xml_buffer, nrg3_temporal_extent_gml_time_period_gml_begin_gml_time_instant_frame xml_buffer, nrg3_temporal_extent_gml_time_period_gml_begin_gml_time_instant_gml_id xml_buffer, nrg3_temporal_extent_gml_time_period_gml_begin_gml_time_instant_gml_related_time{}.relativePosition xml_char(12), nrg3_temporal_extent_gml_time_period_gml_begin_gml_time_instant_gml_related_time{}.xlink_href xml_buffer, nrg3_temporal_extent_gml_time_period_gml_begin_gml_time_instant_gml_related_time{}.gml_time_edge_gml_id xml_buffer, nrg3_temporal_extent_gml_time_period_gml_begin_gml_time_instant_gml_related_time{}.gml_time_edge_gml_related_time{} xml_xml, nrg3_temporal_extent_gml_time_period_gml_begin_gml_time_instant_gml_related_time{}.gml_time_edge_gml_related_time{}.relativePosition xml_char(12), nrg3_temporal_extent_gml_time_period_gml_begin_gml_time_instant_gml_related_time{}.gml_time_edge_gml_related_time{}.xlink_href xml_buffer, nrg3_temporal_extent_gml_time_period_gml_begin_gml_time_instant_gml_related_time{}.gml_time_edge_gml_complex_xlink_href xml_buffer, nrg3_temporal_extent_gml_time_period_gml_begin_gml_time_instant_gml_related_time{}.gml_time_edge_gml_start_xlink_href xml_buffer, nrg3_temporal_extent_gml_time_period_gml_begin_gml_time_instant_gml_related_time{}.gml_time_edge_gml_start_gml_time_node_gml_id xml_buffer, nrg3_temporal_extent_gml_time_period_gml_begin_gml_time_instant_gml_related_time{}.gml_time_edge_gml_start_gml_time_node_gml_related_time{} xml_xml, nrg3_temporal_extent_gml_time_period_gml_begin_gml_time_instant_gml_related_time{}.gml_time_edge_gml_start_gml_time_node_gml_related_time{}.relativePosition xml_char(12), nrg3_temporal_extent_gml_time_period_gml_begin_gml_time_instant_gml_related_time{}.gml_time_edge_gml_start_gml_time_node_gml_related_time{}.xlink_href xml_buffer, nrg3_temporal_extent_gml_time_period_gml_begin_gml_time_instant_gml_related_time{}.gml_time_edge_gml_start_gml_time_node_gml_complex_xlink_href xml_buffer, nrg3_temporal_extent_gml_time_period_gml_begin_gml_time_instant_gml_related_time{}.gml_time_edge_gml_start_gml_time_node_gml_previous_edge{}.xlink_href xml_buffer, nrg3_temporal_extent_gml_time_period_gml_begin_gml_time_instant_gml_related_time{}.gml_time_edge_gml_start_gml_time_node_gml_previous_edge{}.gml_time_edge xml_xml, nrg3_temporal_extent_gml_time_period_gml_begin_gml_time_instant_gml_related_time{}.gml_time_edge_gml_start_gml_time_node_gml_previous_edge{}.gml_time_edge_gml_id xml_buffer,
      nrg3_temporal_extent_gml_time_period_gml_begin_gml_time_instant_gml_related_time{}.gml_time_edge_gml_start_gml_time_node_gml_next_edge{}.xlink_href xml_buffer, nrg3_temporal_extent_gml_time_period_gml_begin_gml_time_instant_gml_related_time{}.gml_time_edge_gml_start_gml_time_node_gml_next_edge{}.gml_time_edge xml_xml, nrg3_temporal_extent_gml_time_period_gml_begin_gml_time_instant_gml_related_time{}.gml_time_edge_gml_start_gml_time_node_gml_next_edge{}.gml_time_edge_gml_id xml_buffer, nrg3_temporal_extent_gml_time_period_gml_begin_gml_time_instant_gml_related_time{}.gml_time_edge_gml_start_gml_time_node_gml_position_xlink_href xml_buffer, nrg3_temporal_extent_gml_time_period_gml_begin_gml_time_instant_gml_related_time{}.gml_time_edge_gml_start_gml_time_node_gml_position_gml_time_instant xml_xml, nrg3_temporal_extent_gml_time_period_gml_begin_gml_time_instant_gml_related_time{}.gml_time_edge_gml_start_gml_time_node_gml_position_gml_time_instant_frame xml_buffer, nrg3_temporal_extent_gml_time_period_gml_begin_gml_time_instant_gml_related_time{}.gml_time_edge_gml_start_gml_time_node_gml_position_gml_time_instant_gml_id xml_buffer, nrg3_temporal_extent_gml_time_period_gml_begin_gml_time_instant_gml_related_time{}.gml_time_edge_gml_end_xlink_href xml_buffer, nrg3_temporal_extent_gml_time_period_gml_begin_gml_time_instant_gml_related_time{}.gml_time_edge_gml_end_gml_time_node_gml_id xml_buffer, nrg3_temporal_extent_gml_time_period_gml_begin_gml_time_instant_gml_related_time{}.gml_time_edge_gml_end_gml_time_node_gml_related_time{} xml_xml, nrg3_temporal_extent_gml_time_period_gml_begin_gml_time_instant_gml_related_time{}.gml_time_edge_gml_end_gml_time_node_gml_related_time{}.relativePosition xml_char(12), nrg3_temporal_extent_gml_time_period_gml_begin_gml_time_instant_gml_related_time{}.gml_time_edge_gml_end_gml_time_node_gml_related_time{}.xlink_href xml_buffer, nrg3_temporal_extent_gml_time_period_gml_begin_gml_time_instant_gml_related_time{}.gml_time_edge_gml_end_gml_time_node_gml_complex_xlink_href xml_buffer, nrg3_temporal_extent_gml_time_period_gml_begin_gml_time_instant_gml_related_time{}.gml_time_edge_gml_end_gml_time_node_gml_previous_edge{}.xlink_href xml_buffer, nrg3_temporal_extent_gml_time_period_gml_begin_gml_time_instant_gml_related_time{}.gml_time_edge_gml_end_gml_time_node_gml_previous_edge{}.gml_time_edge xml_xml, nrg3_temporal_extent_gml_time_period_gml_begin_gml_time_instant_gml_related_time{}.gml_time_edge_gml_end_gml_time_node_gml_previous_edge{}.gml_time_edge_gml_id xml_buffer, nrg3_temporal_extent_gml_time_period_gml_begin_gml_time_instant_gml_related_time{}.gml_time_edge_gml_end_gml_time_node_gml_next_edge{}.xlink_href xml_buffer, nrg3_temporal_extent_gml_time_period_gml_begin_gml_time_instant_gml_related_time{}.gml_time_edge_gml_end_gml_time_node_gml_next_edge{}.gml_time_edge xml_xml, nrg3_temporal_extent_gml_time_period_gml_begin_gml_time_instant_gml_related_time{}.gml_time_edge_gml_end_gml_time_node_gml_next_edge{}.gml_time_edge_gml_id xml_buffer, nrg3_temporal_extent_gml_time_period_gml_begin_gml_time_instant_gml_related_time{}.gml_time_edge_gml_end_gml_time_node_gml_position_xlink_href xml_buffer, nrg3_temporal_extent_gml_time_period_gml_begin_gml_time_instant_gml_related_time{}.gml_time_edge_gml_end_gml_time_node_gml_position_gml_time_instant xml_xml, nrg3_temporal_extent_gml_time_period_gml_begin_gml_time_instant_gml_related_time{}.gml_time_edge_gml_end_gml_time_node_gml_position_gml_time_instant_frame xml_buffer, nrg3_temporal_extent_gml_time_period_gml_begin_gml_time_instant_gml_related_time{}.gml_time_edge_gml_end_gml_time_node_gml_position_gml_time_instant_gml_id xml_buffer, nrg3_temporal_extent_gml_time_period_gml_begin_gml_time_instant_gml_related_time{}.gml_time_edge_gml_extent_xlink_href xml_buffer, nrg3_temporal_extent_gml_time_period_gml_begin_gml_time_instant_gml_related_time{}.gml_time_edge_gml_extent_gml_time_period xml_xml, nrg3_temporal_extent_gml_time_period_gml_begin_gml_time_instant_gml_related_time{}.gml_time_edge_gml_extent_gml_time_period_frame xml_buffer, nrg3_temporal_extent_gml_time_period_gml_begin_gml_time_instant_gml_related_time{}.gml_time_edge_gml_extent_gml_time_period_gml_id xml_buffer, nrg3_temporal_extent_gml_time_period_gml_begin_gml_time_instant_gml_related_time{}.gml_time_instant xml_xml, nrg3_temporal_extent_gml_time_period_gml_begin_gml_time_instant_gml_related_time{}.gml_time_instant_frame xml_buffer, nrg3_temporal_extent_gml_time_period_gml_begin_gml_time_instant_gml_related_time{}.gml_time_instant_gml_id xml_buffer,
      nrg3_temporal_extent_gml_time_period_gml_begin_gml_time_instant_gml_related_time{}.gml_time_node_gml_id xml_buffer, nrg3_temporal_extent_gml_time_period_gml_begin_gml_time_instant_gml_related_time{}.gml_time_node_gml_related_time{} xml_xml, nrg3_temporal_extent_gml_time_period_gml_begin_gml_time_instant_gml_related_time{}.gml_time_node_gml_related_time{}.relativePosition xml_char(12), nrg3_temporal_extent_gml_time_period_gml_begin_gml_time_instant_gml_related_time{}.gml_time_node_gml_related_time{}.xlink_href xml_buffer, nrg3_temporal_extent_gml_time_period_gml_begin_gml_time_instant_gml_related_time{}.gml_time_node_gml_complex_xlink_href xml_buffer, nrg3_temporal_extent_gml_time_period_gml_begin_gml_time_instant_gml_related_time{}.gml_time_node_gml_previous_edge{}.xlink_href xml_buffer, nrg3_temporal_extent_gml_time_period_gml_begin_gml_time_instant_gml_related_time{}.gml_time_node_gml_previous_edge{}.gml_time_edge_gml_id xml_buffer, nrg3_temporal_extent_gml_time_period_gml_begin_gml_time_instant_gml_related_time{}.gml_time_node_gml_previous_edge{}.gml_time_edge_gml_related_time{} xml_xml, nrg3_temporal_extent_gml_time_period_gml_begin_gml_time_instant_gml_related_time{}.gml_time_node_gml_previous_edge{}.gml_time_edge_gml_related_time{}.relativePosition xml_char(12), nrg3_temporal_extent_gml_time_period_gml_begin_gml_time_instant_gml_related_time{}.gml_time_node_gml_previous_edge{}.gml_time_edge_gml_related_time{}.xlink_href xml_buffer, nrg3_temporal_extent_gml_time_period_gml_begin_gml_time_instant_gml_related_time{}.gml_time_node_gml_previous_edge{}.gml_time_edge_gml_complex_xlink_href xml_buffer, nrg3_temporal_extent_gml_time_period_gml_begin_gml_time_instant_gml_related_time{}.gml_time_node_gml_previous_edge{}.gml_time_edge_gml_start_xlink_href xml_buffer, nrg3_temporal_extent_gml_time_period_gml_begin_gml_time_instant_gml_related_time{}.gml_time_node_gml_previous_edge{}.gml_time_edge_gml_start_gml_time_node xml_xml, nrg3_temporal_extent_gml_time_period_gml_begin_gml_time_instant_gml_related_time{}.gml_time_node_gml_previous_edge{}.gml_time_edge_gml_start_gml_time_node_gml_id xml_buffer, nrg3_temporal_extent_gml_time_period_gml_begin_gml_time_instant_gml_related_time{}.gml_time_node_gml_previous_edge{}.gml_time_edge_gml_end_xlink_href xml_buffer, nrg3_temporal_extent_gml_time_period_gml_begin_gml_time_instant_gml_related_time{}.gml_time_node_gml_previous_edge{}.gml_time_edge_gml_end_gml_time_node xml_xml, nrg3_temporal_extent_gml_time_period_gml_begin_gml_time_instant_gml_related_time{}.gml_time_node_gml_previous_edge{}.gml_time_edge_gml_end_gml_time_node_gml_id xml_buffer, nrg3_temporal_extent_gml_time_period_gml_begin_gml_time_instant_gml_related_time{}.gml_time_node_gml_previous_edge{}.gml_time_edge_gml_extent_xlink_href xml_buffer, nrg3_temporal_extent_gml_time_period_gml_begin_gml_time_instant_gml_related_time{}.gml_time_node_gml_previous_edge{}.gml_time_edge_gml_extent_gml_time_period xml_xml, nrg3_temporal_extent_gml_time_period_gml_begin_gml_time_instant_gml_related_time{}.gml_time_node_gml_previous_edge{}.gml_time_edge_gml_extent_gml_time_period_frame xml_buffer, nrg3_temporal_extent_gml_time_period_gml_begin_gml_time_instant_gml_related_time{}.gml_time_node_gml_previous_edge{}.gml_time_edge_gml_extent_gml_time_period_gml_id xml_buffer, nrg3_temporal_extent_gml_time_period_gml_begin_gml_time_instant_gml_related_time{}.gml_time_node_gml_next_edge{}.xlink_href xml_buffer, nrg3_temporal_extent_gml_time_period_gml_begin_gml_time_instant_gml_related_time{}.gml_time_node_gml_next_edge{}.gml_time_edge_gml_id xml_buffer, nrg3_temporal_extent_gml_time_period_gml_begin_gml_time_instant_gml_related_time{}.gml_time_node_gml_next_edge{}.gml_time_edge_gml_related_time{} xml_xml, nrg3_temporal_extent_gml_time_period_gml_begin_gml_time_instant_gml_related_time{}.gml_time_node_gml_next_edge{}.gml_time_edge_gml_related_time{}.relativePosition xml_char(12), nrg3_temporal_extent_gml_time_period_gml_begin_gml_time_instant_gml_related_time{}.gml_time_node_gml_next_edge{}.gml_time_edge_gml_related_time{}.xlink_href xml_buffer, nrg3_temporal_extent_gml_time_period_gml_begin_gml_time_instant_gml_related_time{}.gml_time_node_gml_next_edge{}.gml_time_edge_gml_complex_xlink_href xml_buffer, nrg3_temporal_extent_gml_time_period_gml_begin_gml_time_instant_gml_related_time{}.gml_time_node_gml_next_edge{}.gml_time_edge_gml_start_xlink_href xml_buffer, nrg3_temporal_extent_gml_time_period_gml_begin_gml_time_instant_gml_related_time{}.gml_time_node_gml_next_edge{}.gml_time_edge_gml_start_gml_time_node xml_xml, nrg3_temporal_extent_gml_time_period_gml_begin_gml_time_instant_gml_related_time{}.gml_time_node_gml_next_edge{}.gml_time_edge_gml_start_gml_time_node_gml_id xml_buffer,
      nrg3_temporal_extent_gml_time_period_gml_begin_gml_time_instant_gml_related_time{}.gml_time_node_gml_next_edge{}.gml_time_edge_gml_end_xlink_href xml_buffer, nrg3_temporal_extent_gml_time_period_gml_begin_gml_time_instant_gml_related_time{}.gml_time_node_gml_next_edge{}.gml_time_edge_gml_end_gml_time_node xml_xml, nrg3_temporal_extent_gml_time_period_gml_begin_gml_time_instant_gml_related_time{}.gml_time_node_gml_next_edge{}.gml_time_edge_gml_end_gml_time_node_gml_id xml_buffer, nrg3_temporal_extent_gml_time_period_gml_begin_gml_time_instant_gml_related_time{}.gml_time_node_gml_next_edge{}.gml_time_edge_gml_extent_xlink_href xml_buffer, nrg3_temporal_extent_gml_time_period_gml_begin_gml_time_instant_gml_related_time{}.gml_time_node_gml_next_edge{}.gml_time_edge_gml_extent_gml_time_period xml_xml, nrg3_temporal_extent_gml_time_period_gml_begin_gml_time_instant_gml_related_time{}.gml_time_node_gml_next_edge{}.gml_time_edge_gml_extent_gml_time_period_frame xml_buffer, nrg3_temporal_extent_gml_time_period_gml_begin_gml_time_instant_gml_related_time{}.gml_time_node_gml_next_edge{}.gml_time_edge_gml_extent_gml_time_period_gml_id xml_buffer, nrg3_temporal_extent_gml_time_period_gml_begin_gml_time_instant_gml_related_time{}.gml_time_node_gml_position_xlink_href xml_buffer, nrg3_temporal_extent_gml_time_period_gml_begin_gml_time_instant_gml_related_time{}.gml_time_node_gml_position_gml_time_instant xml_xml, nrg3_temporal_extent_gml_time_period_gml_begin_gml_time_instant_gml_related_time{}.gml_time_node_gml_position_gml_time_instant_frame xml_buffer, nrg3_temporal_extent_gml_time_period_gml_begin_gml_time_instant_gml_related_time{}.gml_time_node_gml_position_gml_time_instant_gml_id xml_buffer, nrg3_temporal_extent_gml_time_period_gml_begin_gml_time_instant_gml_related_time{}.gml_time_period xml_xml, nrg3_temporal_extent_gml_time_period_gml_begin_gml_time_instant_gml_related_time{}.gml_time_period_frame xml_buffer, nrg3_temporal_extent_gml_time_period_gml_begin_gml_time_instant_gml_related_time{}.gml_time_period_gml_id xml_buffer, nrg3_temporal_extent_gml_time_period_gml_begin_gml_time_instant_gml_time_position xml_buffer, nrg3_temporal_extent_gml_time_period_gml_begin_gml_time_instant_gml_time_position_frame xml_buffer, nrg3_temporal_extent_gml_time_period_gml_begin_gml_time_instant_gml_time_position_calendarEraName xml_buffer, nrg3_temporal_extent_gml_time_period_gml_begin_gml_time_instant_gml_time_position_indeterminatePosition xml_char(7), nrg3_temporal_extent_gml_time_period_gml_end_position xml_buffer, nrg3_temporal_extent_gml_time_period_gml_end_position_frame xml_buffer, nrg3_temporal_extent_gml_time_period_gml_end_position_calendarEraName xml_buffer, nrg3_temporal_extent_gml_time_period_gml_end_position_indeterminatePosition xml_char(7), nrg3_temporal_extent_gml_time_period_gml_end_xlink_href xml_buffer, nrg3_temporal_extent_gml_time_period_gml_end_gml_time_instant_frame xml_buffer, nrg3_temporal_extent_gml_time_period_gml_end_gml_time_instant_gml_id xml_buffer, nrg3_temporal_extent_gml_time_period_gml_end_gml_time_instant_gml_related_time{}.relativePosition xml_char(12), nrg3_temporal_extent_gml_time_period_gml_end_gml_time_instant_gml_related_time{}.xlink_href xml_buffer, nrg3_temporal_extent_gml_time_period_gml_end_gml_time_instant_gml_related_time{}.gml_time_edge_gml_id xml_buffer, nrg3_temporal_extent_gml_time_period_gml_end_gml_time_instant_gml_related_time{}.gml_time_edge_gml_related_time{} xml_xml, nrg3_temporal_extent_gml_time_period_gml_end_gml_time_instant_gml_related_time{}.gml_time_edge_gml_related_time{}.relativePosition xml_char(12),
      nrg3_temporal_extent_gml_time_period_gml_end_gml_time_instant_gml_related_time{}.gml_time_edge_gml_related_time{}.xlink_href xml_buffer, nrg3_temporal_extent_gml_time_period_gml_end_gml_time_instant_gml_related_time{}.gml_time_edge_gml_complex_xlink_href xml_buffer, nrg3_temporal_extent_gml_time_period_gml_end_gml_time_instant_gml_related_time{}.gml_time_edge_gml_start_xlink_href xml_buffer, nrg3_temporal_extent_gml_time_period_gml_end_gml_time_instant_gml_related_time{}.gml_time_edge_gml_start_gml_time_node_gml_id xml_buffer, nrg3_temporal_extent_gml_time_period_gml_end_gml_time_instant_gml_related_time{}.gml_time_edge_gml_start_gml_time_node_gml_related_time{} xml_xml, nrg3_temporal_extent_gml_time_period_gml_end_gml_time_instant_gml_related_time{}.gml_time_edge_gml_start_gml_time_node_gml_related_time{}.relativePosition xml_char(12), nrg3_temporal_extent_gml_time_period_gml_end_gml_time_instant_gml_related_time{}.gml_time_edge_gml_start_gml_time_node_gml_related_time{}.xlink_href xml_buffer, nrg3_temporal_extent_gml_time_period_gml_end_gml_time_instant_gml_related_time{}.gml_time_edge_gml_start_gml_time_node_gml_complex_xlink_href xml_buffer, nrg3_temporal_extent_gml_time_period_gml_end_gml_time_instant_gml_related_time{}.gml_time_edge_gml_start_gml_time_node_gml_previous_edge{}.xlink_href xml_buffer, nrg3_temporal_extent_gml_time_period_gml_end_gml_time_instant_gml_related_time{}.gml_time_edge_gml_start_gml_time_node_gml_previous_edge{}.gml_time_edge xml_xml, nrg3_temporal_extent_gml_time_period_gml_end_gml_time_instant_gml_related_time{}.gml_time_edge_gml_start_gml_time_node_gml_previous_edge{}.gml_time_edge_gml_id xml_buffer, nrg3_temporal_extent_gml_time_period_gml_end_gml_time_instant_gml_related_time{}.gml_time_edge_gml_start_gml_time_node_gml_next_edge{}.xlink_href xml_buffer, nrg3_temporal_extent_gml_time_period_gml_end_gml_time_instant_gml_related_time{}.gml_time_edge_gml_start_gml_time_node_gml_next_edge{}.gml_time_edge xml_xml, nrg3_temporal_extent_gml_time_period_gml_end_gml_time_instant_gml_related_time{}.gml_time_edge_gml_start_gml_time_node_gml_next_edge{}.gml_time_edge_gml_id xml_buffer, nrg3_temporal_extent_gml_time_period_gml_end_gml_time_instant_gml_related_time{}.gml_time_edge_gml_start_gml_time_node_gml_position_xlink_href xml_buffer, nrg3_temporal_extent_gml_time_period_gml_end_gml_time_instant_gml_related_time{}.gml_time_edge_gml_start_gml_time_node_gml_position_gml_time_instant xml_xml, nrg3_temporal_extent_gml_time_period_gml_end_gml_time_instant_gml_related_time{}.gml_time_edge_gml_start_gml_time_node_gml_position_gml_time_instant_frame xml_buffer, nrg3_temporal_extent_gml_time_period_gml_end_gml_time_instant_gml_related_time{}.gml_time_edge_gml_start_gml_time_node_gml_position_gml_time_instant_gml_id xml_buffer, nrg3_temporal_extent_gml_time_period_gml_end_gml_time_instant_gml_related_time{}.gml_time_edge_gml_end_xlink_href xml_buffer, nrg3_temporal_extent_gml_time_period_gml_end_gml_time_instant_gml_related_time{}.gml_time_edge_gml_end_gml_time_node_gml_id xml_buffer, nrg3_temporal_extent_gml_time_period_gml_end_gml_time_instant_gml_related_time{}.gml_time_edge_gml_end_gml_time_node_gml_related_time{} xml_xml, nrg3_temporal_extent_gml_time_period_gml_end_gml_time_instant_gml_related_time{}.gml_time_edge_gml_end_gml_time_node_gml_related_time{}.relativePosition xml_char(12), nrg3_temporal_extent_gml_time_period_gml_end_gml_time_instant_gml_related_time{}.gml_time_edge_gml_end_gml_time_node_gml_related_time{}.xlink_href xml_buffer, nrg3_temporal_extent_gml_time_period_gml_end_gml_time_instant_gml_related_time{}.gml_time_edge_gml_end_gml_time_node_gml_complex_xlink_href xml_buffer, nrg3_temporal_extent_gml_time_period_gml_end_gml_time_instant_gml_related_time{}.gml_time_edge_gml_end_gml_time_node_gml_previous_edge{}.xlink_href xml_buffer, nrg3_temporal_extent_gml_time_period_gml_end_gml_time_instant_gml_related_time{}.gml_time_edge_gml_end_gml_time_node_gml_previous_edge{}.gml_time_edge xml_xml, nrg3_temporal_extent_gml_time_period_gml_end_gml_time_instant_gml_related_time{}.gml_time_edge_gml_end_gml_time_node_gml_previous_edge{}.gml_time_edge_gml_id xml_buffer, nrg3_temporal_extent_gml_time_period_gml_end_gml_time_instant_gml_related_time{}.gml_time_edge_gml_end_gml_time_node_gml_next_edge{}.xlink_href xml_buffer, nrg3_temporal_extent_gml_time_period_gml_end_gml_time_instant_gml_related_time{}.gml_time_edge_gml_end_gml_time_node_gml_next_edge{}.gml_time_edge xml_xml, nrg3_temporal_extent_gml_time_period_gml_end_gml_time_instant_gml_related_time{}.gml_time_edge_gml_end_gml_time_node_gml_next_edge{}.gml_time_edge_gml_id xml_buffer,
      nrg3_temporal_extent_gml_time_period_gml_end_gml_time_instant_gml_related_time{}.gml_time_edge_gml_end_gml_time_node_gml_position_xlink_href xml_buffer, nrg3_temporal_extent_gml_time_period_gml_end_gml_time_instant_gml_related_time{}.gml_time_edge_gml_end_gml_time_node_gml_position_gml_time_instant xml_xml, nrg3_temporal_extent_gml_time_period_gml_end_gml_time_instant_gml_related_time{}.gml_time_edge_gml_end_gml_time_node_gml_position_gml_time_instant_frame xml_buffer, nrg3_temporal_extent_gml_time_period_gml_end_gml_time_instant_gml_related_time{}.gml_time_edge_gml_end_gml_time_node_gml_position_gml_time_instant_gml_id xml_buffer, nrg3_temporal_extent_gml_time_period_gml_end_gml_time_instant_gml_related_time{}.gml_time_edge_gml_extent_xlink_href xml_buffer, nrg3_temporal_extent_gml_time_period_gml_end_gml_time_instant_gml_related_time{}.gml_time_edge_gml_extent_gml_time_period xml_xml, nrg3_temporal_extent_gml_time_period_gml_end_gml_time_instant_gml_related_time{}.gml_time_edge_gml_extent_gml_time_period_frame xml_buffer, nrg3_temporal_extent_gml_time_period_gml_end_gml_time_instant_gml_related_time{}.gml_time_edge_gml_extent_gml_time_period_gml_id xml_buffer, nrg3_temporal_extent_gml_time_period_gml_end_gml_time_instant_gml_related_time{}.gml_time_instant xml_xml, nrg3_temporal_extent_gml_time_period_gml_end_gml_time_instant_gml_related_time{}.gml_time_instant_frame xml_buffer, nrg3_temporal_extent_gml_time_period_gml_end_gml_time_instant_gml_related_time{}.gml_time_instant_gml_id xml_buffer, nrg3_temporal_extent_gml_time_period_gml_end_gml_time_instant_gml_related_time{}.gml_time_node_gml_id xml_buffer, nrg3_temporal_extent_gml_time_period_gml_end_gml_time_instant_gml_related_time{}.gml_time_node_gml_related_time{} xml_xml, nrg3_temporal_extent_gml_time_period_gml_end_gml_time_instant_gml_related_time{}.gml_time_node_gml_related_time{}.relativePosition xml_char(12), nrg3_temporal_extent_gml_time_period_gml_end_gml_time_instant_gml_related_time{}.gml_time_node_gml_related_time{}.xlink_href xml_buffer, nrg3_temporal_extent_gml_time_period_gml_end_gml_time_instant_gml_related_time{}.gml_time_node_gml_complex_xlink_href xml_buffer, nrg3_temporal_extent_gml_time_period_gml_end_gml_time_instant_gml_related_time{}.gml_time_node_gml_previous_edge{}.xlink_href xml_buffer, nrg3_temporal_extent_gml_time_period_gml_end_gml_time_instant_gml_related_time{}.gml_time_node_gml_previous_edge{}.gml_time_edge_gml_id xml_buffer, nrg3_temporal_extent_gml_time_period_gml_end_gml_time_instant_gml_related_time{}.gml_time_node_gml_previous_edge{}.gml_time_edge_gml_related_time{} xml_xml, nrg3_temporal_extent_gml_time_period_gml_end_gml_time_instant_gml_related_time{}.gml_time_node_gml_previous_edge{}.gml_time_edge_gml_related_time{}.relativePosition xml_char(12), nrg3_temporal_extent_gml_time_period_gml_end_gml_time_instant_gml_related_time{}.gml_time_node_gml_previous_edge{}.gml_time_edge_gml_related_time{}.xlink_href xml_buffer, nrg3_temporal_extent_gml_time_period_gml_end_gml_time_instant_gml_related_time{}.gml_time_node_gml_previous_edge{}.gml_time_edge_gml_complex_xlink_href xml_buffer, nrg3_temporal_extent_gml_time_period_gml_end_gml_time_instant_gml_related_time{}.gml_time_node_gml_previous_edge{}.gml_time_edge_gml_start_xlink_href xml_buffer, nrg3_temporal_extent_gml_time_period_gml_end_gml_time_instant_gml_related_time{}.gml_time_node_gml_previous_edge{}.gml_time_edge_gml_start_gml_time_node xml_xml, nrg3_temporal_extent_gml_time_period_gml_end_gml_time_instant_gml_related_time{}.gml_time_node_gml_previous_edge{}.gml_time_edge_gml_start_gml_time_node_gml_id xml_buffer, nrg3_temporal_extent_gml_time_period_gml_end_gml_time_instant_gml_related_time{}.gml_time_node_gml_previous_edge{}.gml_time_edge_gml_end_xlink_href xml_buffer, nrg3_temporal_extent_gml_time_period_gml_end_gml_time_instant_gml_related_time{}.gml_time_node_gml_previous_edge{}.gml_time_edge_gml_end_gml_time_node xml_xml, nrg3_temporal_extent_gml_time_period_gml_end_gml_time_instant_gml_related_time{}.gml_time_node_gml_previous_edge{}.gml_time_edge_gml_end_gml_time_node_gml_id xml_buffer, nrg3_temporal_extent_gml_time_period_gml_end_gml_time_instant_gml_related_time{}.gml_time_node_gml_previous_edge{}.gml_time_edge_gml_extent_xlink_href xml_buffer, nrg3_temporal_extent_gml_time_period_gml_end_gml_time_instant_gml_related_time{}.gml_time_node_gml_previous_edge{}.gml_time_edge_gml_extent_gml_time_period xml_xml,
      nrg3_temporal_extent_gml_time_period_gml_end_gml_time_instant_gml_related_time{}.gml_time_node_gml_previous_edge{}.gml_time_edge_gml_extent_gml_time_period_frame xml_buffer, nrg3_temporal_extent_gml_time_period_gml_end_gml_time_instant_gml_related_time{}.gml_time_node_gml_previous_edge{}.gml_time_edge_gml_extent_gml_time_period_gml_id xml_buffer, nrg3_temporal_extent_gml_time_period_gml_end_gml_time_instant_gml_related_time{}.gml_time_node_gml_next_edge{}.xlink_href xml_buffer, nrg3_temporal_extent_gml_time_period_gml_end_gml_time_instant_gml_related_time{}.gml_time_node_gml_next_edge{}.gml_time_edge_gml_id xml_buffer, gml_description xml_buffer, gml_name xml_buffer, nrg3_temporal_extent_gml_time_period_gml_end_gml_time_instant_gml_related_time{}.gml_time_node_gml_next_edge{}.gml_time_edge_gml_related_time{} xml_xml, nrg3_temporal_extent_gml_time_period_gml_end_gml_time_instant_gml_related_time{}.gml_time_node_gml_next_edge{}.gml_time_edge_gml_related_time{}.relativePosition xml_char(12), nrg3_temporal_extent_gml_time_period_gml_end_gml_time_instant_gml_related_time{}.gml_time_node_gml_next_edge{}.gml_time_edge_gml_related_time{}.xlink_href xml_buffer, nrg3_temporal_extent_gml_time_period_gml_end_gml_time_instant_gml_related_time{}.gml_time_node_gml_next_edge{}.gml_time_edge_gml_complex_xlink_href xml_buffer, nrg3_temporal_extent_gml_time_period_gml_end_gml_time_instant_gml_related_time{}.gml_time_node_gml_next_edge{}.gml_time_edge_gml_start_xlink_href xml_buffer, nrg3_temporal_extent_gml_time_period_gml_end_gml_time_instant_gml_related_time{}.gml_time_node_gml_next_edge{}.gml_time_edge_gml_start_gml_time_node xml_xml, nrg3_temporal_extent_gml_time_period_gml_end_gml_time_instant_gml_related_time{}.gml_time_node_gml_next_edge{}.gml_time_edge_gml_start_gml_time_node_gml_id xml_buffer, nrg3_temporal_extent_gml_time_period_gml_end_gml_time_instant_gml_related_time{}.gml_time_node_gml_next_edge{}.gml_time_edge_gml_end_xlink_href xml_buffer, nrg3_temporal_extent_gml_time_period_gml_end_gml_time_instant_gml_related_time{}.gml_time_node_gml_next_edge{}.gml_time_edge_gml_end_gml_time_node xml_xml, nrg3_temporal_extent_gml_time_period_gml_end_gml_time_instant_gml_related_time{}.gml_time_node_gml_next_edge{}.gml_time_edge_gml_end_gml_time_node_gml_id xml_buffer, nrg3_temporal_extent_gml_time_period_gml_end_gml_time_instant_gml_related_time{}.gml_time_node_gml_next_edge{}.gml_time_edge_gml_extent_xlink_href xml_buffer, nrg3_temporal_extent_gml_time_period_gml_end_gml_time_instant_gml_related_time{}.gml_time_node_gml_next_edge{}.gml_time_edge_gml_extent_gml_time_period xml_xml, nrg3_temporal_extent_gml_time_period_gml_end_gml_time_instant_gml_related_time{}.gml_time_node_gml_next_edge{}.gml_time_edge_gml_extent_gml_time_period_frame xml_buffer, nrg3_temporal_extent_gml_time_period_gml_end_gml_time_instant_gml_related_time{}.gml_time_node_gml_next_edge{}.gml_time_edge_gml_extent_gml_time_period_gml_id xml_buffer, nrg3_temporal_extent_gml_time_period_gml_end_gml_time_instant_gml_related_time{}.gml_time_node_gml_position_xlink_href xml_buffer, nrg3_temporal_extent_gml_time_period_gml_end_gml_time_instant_gml_related_time{}.gml_time_node_gml_position_gml_time_instant xml_xml, nrg3_temporal_extent_gml_time_period_gml_end_gml_time_instant_gml_related_time{}.gml_time_node_gml_position_gml_time_instant_frame xml_buffer, nrg3_temporal_extent_gml_time_period_gml_end_gml_time_instant_gml_related_time{}.gml_time_node_gml_position_gml_time_instant_gml_id xml_buffer, nrg3_temporal_extent_gml_time_period_gml_end_gml_time_instant_gml_related_time{}.gml_time_period xml_xml, nrg3_temporal_extent_gml_time_period_gml_end_gml_time_instant_gml_related_time{}.gml_time_period_frame xml_buffer, nrg3_temporal_extent_gml_time_period_gml_end_gml_time_instant_gml_related_time{}.gml_time_period_gml_id xml_buffer, nrg3_temporal_extent_gml_time_period_gml_end_gml_time_instant_gml_time_position xml_buffer, nrg3_temporal_extent_gml_time_period_gml_end_gml_time_instant_gml_time_position_frame xml_buffer, nrg3_temporal_extent_gml_time_period_gml_end_gml_time_instant_gml_time_position_calendarEraName xml_buffer,
      nrg3_temporal_extent_gml_time_period_gml_end_gml_time_instant_gml_time_position_indeterminatePosition xml_char(7), nrg3_temporal_extent_gml_time_period_gml_duration xml_buffer, nrg3_temporal_extent_gml_time_period_gml_time_interval xml_real64, nrg3_temporal_extent_gml_time_period_gml_time_interval_unit xml_buffer, nrg3_temporal_extent_gml_time_period_gml_time_interval_radix xml_uint64, nrg3_temporal_extent_gml_time_period_gml_time_interval_factor xml_int64, nrg3_time_interval xml_real64, nrg3_time_interval_unit xml_buffer, nrg3_time_interval_radix xml_uint64, nrg3_time_interval_factor xml_int64, nrg3_number_of_header_lines xml_int64, nrg3_field_separator xml_buffer, nrg3_record_separator xml_buffer, nrg3_decimal_symbol xml_buffer, nrg3_value_column_number xml_int64
    -> Junction_49
nrg3_TypicalValuesTimeSeries (reader CITYGML_2)
    attributes: citygml_target_uri xml_buffer, citygml_feature_role xml_buffer, citygml_feature_role_attr_name xml_buffer, citygml_feature_role_attr_val xml_buffer, gml_description xml_buffer, gml_name xml_buffer, nrg3_acquisition_method xml_buffer, nrg3_acquisition_method_codeSpace xml_buffer, nrg3_interpolation_type xml_char(28), nrg3_source xml_buffer, nrg3_start_time xml_time, nrg3_start_day xml_int64, nrg3_start_month xml_int64, nrg3_temporal_extent xml_real64, nrg3_temporal_extent_unit xml_buffer, nrg3_temporal_extent_radix xml_uint64, nrg3_temporal_extent_factor xml_int64, nrg3_time_interval xml_real64, nrg3_time_interval_unit xml_buffer, nrg3_time_interval_radix xml_uint64, nrg3_time_interval_factor xml_int64, nrg3_values_list xml_buffer, nrg3_values_list_units xml_buffer
    -> Junction_49
nrg3_TypicalValuesTimeSeriesFile (reader CITYGML_2)
    attributes: citygml_target_uri xml_buffer, citygml_feature_role xml_buffer, citygml_feature_role_attr_name xml_buffer, citygml_feature_role_attr_val xml_buffer, gml_description xml_buffer, gml_name xml_buffer, nrg3_acquisition_method xml_buffer, nrg3_acquisition_method_codeSpace xml_buffer, nrg3_interpolation_type xml_char(28), nrg3_source xml_buffer, nrg3_start_time xml_time, nrg3_start_day xml_int64, nrg3_start_month xml_int64, nrg3_uom_units xml_buffer, nrg3_file_uri xml_buffer, nrg3_temporal_extent xml_real64, nrg3_temporal_extent_unit xml_buffer, nrg3_temporal_extent_radix xml_uint64, nrg3_temporal_extent_factor xml_int64, nrg3_time_interval xml_real64, nrg3_time_interval_unit xml_buffer, nrg3_time_interval_radix xml_uint64, nrg3_time_interval_factor xml_int64, nrg3_number_of_header_lines xml_int64, nrg3_field_separator xml_buffer, nrg3_record_separator xml_buffer, nrg3_decimal_symbol xml_buffer, nrg3_value_column_number xml_int64
    -> Junction_49
nrg3_SensorConnection (reader CITYGML_2)
    attributes: citygml_target_uri xml_buffer, citygml_feature_role xml_buffer, citygml_feature_role_attr_name xml_buffer, citygml_feature_role_attr_val xml_buffer, gml_description xml_buffer, gml_name xml_buffer, nrg3_acquisition_method xml_buffer, nrg3_acquisition_method_codeSpace xml_buffer, nrg3_interpolation_type xml_char(28), nrg3_source xml_buffer, nrg3_temporal_extent xml_real64, nrg3_temporal_extent_unit xml_buffer, nrg3_temporal_extent_radix xml_uint64, nrg3_temporal_extent_factor xml_int64, nrg3_connection_type xml_buffer, nrg3_connection_type_codeSpace xml_buffer, nrg3_observation_property xml_buffer, nrg3_uom_units xml_buffer, nrg3_sensor_id xml_buffer, nrg3_sensor_name xml_buffer, nrg3_observation_id xml_buffer, nrg3_datastream_id xml_buffer, nrg3_base_url xml_buffer, nrg3_auth_type xml_buffer, nrg3_auth_type_codeSpace xml_buffer, nrg3_mqtt_server xml_buffer, nrg3_mqtt_topic xml_buffer, nrg3_link_to_observation xml_buffer, nrg3_link_to_sensor_description xml_buffer
    -> Junction_49

Bookmark: Weather Data
Junction_21
    -> ADE_Feature_editor_9 [objectclass_name_list]
nrg3_WeatherData (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_type xml_buffer, nrg3_type_codeSpace xml_buffer, nrg3_value_type xml_buffer, nrg3_value_type_codeSpace xml_buffer, nrg3_yearly_value xml_real64, nrg3_yearly_value_units xml_buffer, nrg3_time_dependent_values_xlink_href xml_buffer
    -> ADE_Feature_editor_9 [ADE_Feature]

Bookmark: Weather Station
Junction_59
    -> ADE_CityObject_editor_4 [objectclass_name_list]
nrg3_WeatherStation (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer
    -> ADE_CityObject_editor_4 [ADE_CityObject]

Bookmark: Devices
Junction_23
    -> ADE_Feature_editor_10 [objectclass_name_list]
    -> ADE_CityObject_editor_5 [objectclass_name_list]
Junction_26
    -> Junction_19
    -> ADE_CityObject_editor_6 [objectclass_name_list]
Junction_27
    -> ADE_CityObject_editor_7 [objectclass_name_list]
nrg3_DeviceOperation (reader CITYGML_2)
    attributes: citygml_target_uri xml_buffer, citygml_feature_role xml_buffer, citygml_feature_role_attr_name xml_buffer, citygml_feature_role_attr_val xml_buffer, gml_description xml_buffer, gml_name xml_buffer, nrg3_type xml_buffer, nrg3_type_codeSpace xml_buffer, nrg3_yearly_global_efficiency xml_real64, nrg3_schedule_xlink_href xml_buffer
    -> ADE_Feature_editor_10 [ADE_Feature]
nrg3_Boiler (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_has_condensation xml_boolean
    -> Junction_181
nrg3_GenericDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer
    -> Junction_181
nrg3_GenericElectricalDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer
    -> Junction_181
nrg3_HeatPump (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_heat_source xml_buffer, nrg3_heat_source_codeSpace xml_buffer, nrg3_cop_source_temperature xml_real64, nrg3_cop_source_temperature_units xml_buffer, nrg3_cop_operation_temperature xml_real64, nrg3_cop_operation_temperature_units xml_buffer
    -> Junction_181
nrg3_LightingDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer
    -> Junction_181
nrg3_MovableShadingDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_type xml_buffer, nrg3_type_codeSpace xml_buffer, nrg3_installation_side xml_char(7), nrg3_maximum_cover_ratio xml_real64, nrg3_maximum_cover_ratio_units xml_buffer, nrg3_transmittance_nrg3_transmittance_nrg3_fraction xml_real64, nrg3_transmittance_nrg3_transmittance_nrg3_fraction_units xml_buffer, nrg3_transmittance_nrg3_transmittance_nrg3_wavelength_range xml_char(8)
    -> Junction_181
nrg3_ElectricalStorageDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_battery_technology xml_buffer, nrg3_battery_technology_codeSpace xml_buffer, nrg3_power_capacity xml_real64, nrg3_power_capacity_units xml_buffer
    -> Junction_185
nrg3_ThermalStorageDevice (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_preparation_temperature xml_real64, nrg3_preparation_temperature_units xml_buffer, nrg3_medium xml_buffer, nrg3_medium_codeSpace xml_buffer, nrg3_thermal_losses_factor xml_real64, nrg3_thermal_losses_factor_units xml_buffer, nrg3_volume xml_real64, nrg3_volume_units xml_buffer
    -> Junction_185
nrg3_GenericSolarCollector (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_module_area xml_real64, nrg3_module_area_units xml_buffer, nrg3_aperture_area xml_real64, nrg3_aperture_area_units xml_buffer, nrg3_azimuth xml_real64, nrg3_azimuth_units xml_buffer, nrg3_inclination xml_real64, nrg3_inclination_units xml_buffer, citygml_level_of_detail{} xml_buffer
    -> Junction_186
nrg3_PhotovoltaicCollector (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_module_area xml_real64, nrg3_module_area_units xml_buffer, nrg3_aperture_area xml_real64, nrg3_aperture_area_units xml_buffer, nrg3_azimuth xml_real64, nrg3_azimuth_units xml_buffer, nrg3_inclination xml_real64, nrg3_inclination_units xml_buffer, citygml_level_of_detail{} xml_buffer, nrg3_cell_type xml_buffer, nrg3_cell_type_codeSpace xml_buffer
    -> Junction_186
nrg3_PhotovoltaicThermalCollector (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_module_area xml_real64, nrg3_module_area_units xml_buffer, nrg3_aperture_area xml_real64, nrg3_aperture_area_units xml_buffer, nrg3_azimuth xml_real64, nrg3_azimuth_units xml_buffer, nrg3_inclination xml_real64, nrg3_inclination_units xml_buffer, citygml_level_of_detail{} xml_buffer, nrg3_type xml_buffer, nrg3_type_codeSpace xml_buffer, nrg3_cell_type xml_buffer, nrg3_cell_type_codeSpace xml_buffer, nrg3_optical_efficiency xml_real64,
      nrg3_optical_efficiency_units xml_buffer, nrg3_linear_heat_loss_coefficient xml_real64, nrg3_quadratic_heat_loss_coefficient xml_real64
    -> Junction_186
nrg3_SolarThermalCollector (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_model xml_buffer,
      nrg3_year_of_manufacture xml_int64, nrg3_number_of_devices xml_int64, nrg3_installed_power xml_real64, nrg3_installed_power_units xml_buffer, nrg3_nominal_efficiency xml_real64, nrg3_nominal_efficiency_units xml_buffer, nrg3_efficiency_indicator xml_buffer, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_device_operation{}.xlink_href xml_buffer, nrg3_module_area xml_real64, nrg3_module_area_units xml_buffer, nrg3_aperture_area xml_real64, nrg3_aperture_area_units xml_buffer, nrg3_azimuth xml_real64, nrg3_azimuth_units xml_buffer, nrg3_inclination xml_real64, nrg3_inclination_units xml_buffer, citygml_level_of_detail{} xml_buffer, nrg3_type xml_buffer, nrg3_type_codeSpace xml_buffer, nrg3_optical_efficiency xml_real64, nrg3_optical_efficiency_units xml_buffer, nrg3_linear_heat_loss_coefficient xml_real64,
      nrg3_quadratic_heat_loss_coefficient xml_real64
    -> Junction_186

Bookmark: OPTICAL PROPERTY
Junction_19
    -> FeatureMerger_58 [SUPPLIER]
GeometryRemover_17
    REMOVE_COORDSYS = No
    -> AttributeFilter_5
AttributeFilter_5
    ATTR_NAME = transmittance_transmittance_fraction
    ATTR_VALUES = <Empty>,<Missing>,<Null>,<Unfiltered>
    <UNFILTERED> -> AttributeKeeper_34
AttributeKeeper_34
    CREATE_BULK_MODE_FEATURES = NO
    KEEP_ATTRS = transmittance_transmittance_fraction,transmittance_transmittance_fraction_uom,transmittance_transmittance_wavelength_range,id
    -> AttributeRenamer_60
AttributeRenamer_60
    ATTR_TABLE = RENAME_SET_DEFAULT id > device_id
    KEEP_RENAMED_ONLY = no
    MISSING_INPUT_ATTRS = REMOVE
    -> BulkAttributeRenamer_30
BulkAttributeRenamer_30
    ATTRCHOICE_ACTION = NONPROTECTEDFME
    CASE_DISP = NO
    MODE_CHOICE = RENAME
    PATTERN_ACTION_DISP = STRINGREPLACE
    REPLACE_PATTERN = transmittance_transmittance_
    ATTRCHOICE = All Attributes
    -> AttributeCreator_27
Note: Add objectclass_name
AttributeCreator_27
    ATTR_TABLE = SET_TO objectclass_name (varchar(15)) = Transmittance
    -> FeatureMerger_58 [REQUESTOR]
FeatureMerger_58
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter_17
Sorter_17
    SORT_PARM = device_id NATURAL ASCENDING objectclass_id NATURAL ASCENDING
    SORTED -> Counter_28
Counter_28
    CNT_ATTR = id
    DOMAIN = @Value(table_name)
    SCOPE = Global
    START = 0
    -> FeatureWriter_27 [citydb.ng3_optical_property]
Note: Insert into ng3_OPTICAL_PROPERTIES
FeatureWriter_27
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_optical_property -> AttributeKeeper_36
AttributeKeeper_36
    CREATE_BULK_MODE_FEATURES = NO
    KEEP_ATTRS = id,device_id
    -> AttributeRenamer_19
AttributeRenamer_19
    ATTR_TABLE:
      RENAME_SET_DEFAULT id > transmittance_id
      RENAME_SET_DEFAULT device_id > id
    KEEP_RENAMED_ONLY = no
    MISSING_INPUT_ATTRS = REMOVE
    -> FeatureMerger_25 [SUPPLIER]
    -> FeatureMerger_26 [SUPPLIER]
    -> FeatureMerger_59 [SUPPLIER]

Bookmark: Urban Function Area
Junction_30
    -> ADE_CityObject_editor_8 [objectclass_name_list]
nrg3_UrbanFunctionArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_group_member{}.role xml_buffer, citygml_group_member{}.xlink_href xml_buffer, citygml_parent_xlink_href xml_buffer, citygml_level_of_detail{} xml_buffer, nrg3_type xml_buffer, nrg3_type_codeSpace xml_buffer, nrg3_code xml_buffer, nrg3_code_codeSpace xml_buffer
    -> ADE_CityObject_editor_8 [ADE_CityObject]

Bookmark: Resources
Junction_29
    -> ADE_Feature_editor_11 [objectclass_name_list]
nrg3_Energy (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer, nrg3_energy_carrier xml_buffer,
      nrg3_energy_carrier_codeSpace xml_buffer, nrg3_maximum_load xml_real64, nrg3_maximum_load_units xml_buffer, nrg3_source xml_buffer, nrg3_source_codeSpace xml_buffer
    -> Junction_187
nrg3_Water (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer
    -> Junction_187
nrg3_ConstructionMaterial (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer
    -> Junction_187
nrg3_Food (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer
    -> Junction_187
nrg3_OtherResource (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer
    -> Junction_187
nrg3_UrbanSpace (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer
    -> Junction_187
nrg3_Waste (reader CITYGML_2)
    attributes: citygml_target_uri xml_buffer, citygml_feature_role xml_buffer, citygml_feature_role_attr_name xml_buffer, citygml_feature_role_attr_val xml_buffer, gml_description xml_buffer, gml_name xml_buffer, nrg3_status xml_char(9), nrg3_operation_type xml_buffer, nrg3_operation_type_codeSpace xml_buffer, nrg3_amount_type xml_buffer, nrg3_amount_type_codeSpace xml_buffer, nrg3_year xml_int64, nrg3_amount xml_real64, nrg3_amount_units xml_buffer, nrg3_time_dependent_amount_xlink_href xml_buffer, nrg3_is_amount_normalized xml_boolean, nrg3_normalization_value xml_real64, nrg3_normalization_value_units xml_buffer, nrg3_normalization_parameter xml_buffer, nrg3_co2_equivalent xml_real64, nrg3_co2_equivalent_units xml_buffer, nrg3_costs_money xml_real64, nrg3_costs_money_units xml_buffer, nrg3_yields_money xml_real64, nrg3_yields_money_units xml_buffer, nrg3_type xml_buffer, nrg3_type_codeSpace xml_buffer, nrg3_end_use xml_buffer, nrg3_end_use_codeSpace xml_buffer, nrg3_is_dangerous xml_boolean,
      nrg3_is_recyclable xml_boolean
    -> Junction_187

Bookmark: Core
Junction_31
    -> ADE_Feature_editor_14 [objectclass_name_list]
    -> ADE_Feature_editor_13 [objectclass_name_list]
    -> ADE_Feature_editor_12 [objectclass_name_list]
nrg3_UtilityNetworkConnection (reader CITYGML_2)
    attributes: citygml_target_uri xml_buffer, citygml_feature_role xml_buffer, citygml_feature_role_attr_name xml_buffer, citygml_feature_role_attr_val xml_buffer, gml_description xml_buffer, gml_name xml_buffer, nrg3_network_type xml_buffer, nrg3_network_type_codeSpace xml_buffer, nrg3_connection_status xml_char(29), nrg3_function_in_network xml_buffer, nrg3_function_in_network_codeSpace xml_buffer, nrg3_usage_in_network xml_buffer, nrg3_usage_in_network_codeSpace xml_buffer, nrg3_network_id xml_buffer, nrg3_network_node_id xml_buffer
    -> ADE_Feature_editor_12 [ADE_Feature]
nrg3_RefurbishmentMeasure (reader CITYGML_2)
    attributes: citygml_target_uri xml_buffer, citygml_feature_role xml_buffer, citygml_feature_role_attr_name xml_buffer, citygml_feature_role_attr_val xml_buffer, gml_description xml_buffer, gml_name xml_buffer, nrg3_library_code xml_buffer, nrg3_library_code_codeSpace xml_buffer, nrg3_type xml_buffer, nrg3_type_codeSpace xml_buffer, nrg3_start_date xml_date, nrg3_end_date xml_date
    -> ADE_Feature_editor_13 [ADE_Feature]
nrg3_EnergyPerformanceCertificate (reader CITYGML_2)
    attributes: citygml_target_uri xml_buffer, citygml_feature_role xml_buffer, citygml_feature_role_attr_name xml_buffer, citygml_feature_role_attr_val xml_buffer, gml_description xml_buffer, gml_name xml_buffer, nrg3_type xml_buffer, nrg3_type_codeSpace xml_buffer, nrg3_label xml_buffer, nrg3_value xml_real64, nrg3_value_units xml_buffer, nrg3_issue_date xml_date, nrg3_expiration_date xml_date, nrg3_certification_method xml_buffer, nrg3_certification_uri xml_buffer
    -> ADE_Feature_editor_14 [ADE_Feature]

Bookmark: Building physics
Junction_35
    -> Junction_39
    -> ADE_CityObject_editor_10 [objectclass_name_list]
    -> ADE_CityObject_editor_9 [objectclass_name_list]
Note: QualifiedAttributeWriter_2 : objectclass_nale_list
Junction_39
    -> Junction_41
Junction_37
    -> ADE_CityObject_editor_13 [objectclass_name_list]
    -> ADE_CityObject_editor_15 [objectclass_name_list]
nrg3_PartyWallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_188
nrg3_IntermediateFloorSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_188
nrg3_BasementCeilingSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_188
nrg3_AtticFloorSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_188
nrg3_ThermalZone (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_area{}.nrg3_qualified_area_nrg3_description xml_buffer,
      nrg3_area{}.nrg3_qualified_area_nrg3_source xml_buffer, nrg3_area{}.nrg3_qualified_area_nrg3_value xml_real64, nrg3_area{}.nrg3_qualified_area_nrg3_value_units xml_buffer, nrg3_area{}.nrg3_qualified_area_nrg3_type xml_buffer, nrg3_area{}.nrg3_qualified_area_nrg3_type_codeSpace xml_buffer, nrg3_volume{}.nrg3_qualified_volume_nrg3_description xml_buffer, nrg3_volume{}.nrg3_qualified_volume_nrg3_source xml_buffer, nrg3_volume{}.nrg3_qualified_volume_nrg3_value xml_real64, nrg3_volume{}.nrg3_qualified_volume_nrg3_value_units xml_buffer, nrg3_volume{}.nrg3_qualified_volume_nrg3_type xml_buffer, nrg3_volume{}.nrg3_qualified_volume_nrg3_type_codeSpace xml_buffer, citygml_level_of_detail{} xml_buffer, nrg3_usage_zone{}.xlink_href xml_buffer, nrg3_heat_capacity xml_real64, nrg3_heat_capacity_units xml_buffer, nrg3_infiltration_rate xml_real64, nrg3_infiltration_rate_units xml_buffer, nrg3_is_cooled xml_boolean, nrg3_is_heated xml_boolean, nrg3_coincides_with_lod2_hull xml_boolean, nrg3_coincides_with_lod3_hull xml_boolean, nrg3_thermal_boundary{}.xlink_href xml_buffer
    -> ADE_CityObject_editor_9 [ADE_CityObject]
Note: CityObject_editor_5 : Thematics Surfaces not_in_database
Junction_54
    -> ADE_CityObject_editor_15 [ADE_CityObject]
Note: CityObject_editor_6 : Openings_not_in_database
Junction_52
    -> ADE_CityObject_editor_13 [ADE_CityObject]

Bookmark: Occupancy
Junction_36
    -> ADE_Feature_editor [objectclass_name_list]
    -> Junction_42
    -> Junction_44
    -> ADE_CityObject_editor_12 [objectclass_name_list]
    -> ADE_CityObject_editor_11 [objectclass_name_list]
Note: QualifiedAttributeWriter_3 : objectclass_nale_list
Junction_42
    -> Junction_43
Note: QualifiedAttributeWriter_5 : objectclass_name_list
Junction_44
    -> Junction_45
nrg3_UsageZone (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_area{}.nrg3_qualified_area_nrg3_description xml_buffer,
      nrg3_area{}.nrg3_qualified_area_nrg3_source xml_buffer, nrg3_area{}.nrg3_qualified_area_nrg3_value xml_real64, nrg3_area{}.nrg3_qualified_area_nrg3_value_units xml_buffer, nrg3_area{}.nrg3_qualified_area_nrg3_type xml_buffer, nrg3_area{}.nrg3_qualified_area_nrg3_type_codeSpace xml_buffer, nrg3_volume{}.nrg3_qualified_volume_nrg3_description xml_buffer, nrg3_volume{}.nrg3_qualified_volume_nrg3_source xml_buffer, nrg3_volume{}.nrg3_qualified_volume_nrg3_value xml_real64, nrg3_volume{}.nrg3_qualified_volume_nrg3_value_units xml_buffer, nrg3_volume{}.nrg3_qualified_volume_nrg3_type xml_buffer, nrg3_volume{}.nrg3_qualified_volume_nrg3_type_codeSpace xml_buffer, citygml_level_of_detail{} xml_buffer, nrg3_building_unit{}.xlink_href xml_buffer, nrg3_type xml_buffer, nrg3_type_codeSpace xml_buffer, nrg3_is_primary xml_boolean, nrg3_number_of_building_units xml_int64, nrg3_internal_heat_gains xml_real64, nrg3_internal_heat_gains_units xml_buffer, nrg3_internal_heat_gains_convective_fraction xml_real64, nrg3_internal_heat_gains_convective_fraction_units xml_buffer, nrg3_internal_heat_gains_latent_fraction xml_real64, nrg3_internal_heat_gains_latent_fraction_units xml_buffer, nrg3_internal_heat_gains_radiant_fraction xml_real64, nrg3_internal_heat_gains_radiant_fraction_units xml_buffer, nrg3_cooling_schedule_xlink_href xml_buffer, nrg3_heating_schedule_xlink_href xml_buffer, nrg3_ventilation_schedule_xlink_href xml_buffer, nrg3_occupied_by{}.xlink_href xml_buffer
    -> ADE_CityObject_editor_11 [ADE_CityObject]
nrg3_BuildingUnit (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, nrg3_area{}.nrg3_qualified_area_nrg3_description xml_buffer,
      nrg3_area{}.nrg3_qualified_area_nrg3_source xml_buffer, nrg3_area{}.nrg3_qualified_area_nrg3_value xml_real64, nrg3_area{}.nrg3_qualified_area_nrg3_value_units xml_buffer, nrg3_area{}.nrg3_qualified_area_nrg3_type xml_buffer, nrg3_area{}.nrg3_qualified_area_nrg3_type_codeSpace xml_buffer, nrg3_volume{}.nrg3_qualified_volume_nrg3_description xml_buffer, nrg3_volume{}.nrg3_qualified_volume_nrg3_source xml_buffer, nrg3_volume{}.nrg3_qualified_volume_nrg3_value xml_real64, nrg3_volume{}.nrg3_qualified_volume_nrg3_value_units xml_buffer, nrg3_volume{}.nrg3_qualified_volume_nrg3_type xml_buffer, nrg3_volume{}.nrg3_qualified_volume_nrg3_type_codeSpace xml_buffer, citygml_level_of_detail{} xml_buffer, nrg3_type xml_buffer, nrg3_type_codeSpace xml_buffer, nrg3_number_of_rooms xml_int64, nrg3_owner_name xml_buffer, nrg3_ownership_type xml_buffer, nrg3_ownership_type_codeSpace xml_buffer, nrg3_address{}.xlink_href xml_buffer, nrg3_energy_performance_certificate{}.xlink_href xml_buffer, nrg3_refurbishment_measure{}.xlink_href xml_buffer, nrg3_occupied_by{}.xlink_href xml_buffer
    -> ADE_CityObject_editor_12 [ADE_CityObject]
nrg3_Occupants (reader CITYGML_2)
    attributes: citygml_target_uri xml_buffer, citygml_feature_role xml_buffer, citygml_feature_role_attr_name xml_buffer, citygml_feature_role_attr_val xml_buffer, gml_description xml_buffer, gml_name xml_buffer, nrg3_type xml_buffer, nrg3_type_codeSpace xml_buffer, nrg3_number_of_occupants xml_int64, nrg3_heat_dissipation xml_real64, nrg3_heat_dissipation_units xml_buffer, nrg3_heat_dissipation_convective_fraction xml_real64, nrg3_heat_dissipation_convective_fraction_units xml_buffer, nrg3_heat_dissipation_latent_fraction xml_real64, nrg3_heat_dissipation_latent_fraction_units xml_buffer, nrg3_heat_dissipation_radiant_fraction xml_real64, nrg3_heat_dissipation_radiant_fraction_units xml_buffer, nrg3_occupancy_rate_xlink_href xml_buffer, nrg3_average_diet_type xml_buffer, nrg3_average_diet_type_codeSpace xml_buffer, nrg3_average_income_level xml_buffer, nrg3_average_income_level_codeSpace xml_buffer, nrg3_average_instruction_level xml_buffer, nrg3_average_instruction_level_codeSpace xml_buffer
    -> ADE_Feature_editor [ADE_Feature]

Bookmark: Suitability
Junction_117
    -> AttributeKeeper_23
    -> Junction_167
AttributeKeeper_23
    CREATE_BULK_MODE_FEATURES = NO
    KEEP_ATTRS = objectclass_name,table_name
    -> FeatureMerger_7 [SUPPLIER]
Junction_96
    -> AttributeKeeper_15
AttributeKeeper_15
    CREATE_BULK_MODE_FEATURES = NO
    KEEP_ATTRS = id,gmlid
    -> AttributeRenamer_12
AttributeRenamer_12
    ATTR_TABLE:
      RENAME_SET_DEFAULT gmlid > gml_link
      RENAME_SET_DEFAULT id > schedule_id
    KEEP_RENAMED_ONLY = no
    MISSING_INPUT_ATTRS = REMOVE
    -> FeatureMerger_8 [SUPPLIER]
Junction_170
    -> AttributeKeeper_12
AttributeKeeper_12
    CREATE_BULK_MODE_FEATURES = NO
    KEEP_ATTRS = id
    KEEP_LIST = suitability{}
    -> AttributeRenamer_79
AttributeRenamer_79
    ATTR_TABLE = RENAME_SET_DEFAULT id > cityobject_id
    KEEP_RENAMED_ONLY = no
    MISSING_INPUT_ATTRS = REMOVE
    -> ListExploder_4
ListExploder_4
    ATTR_ACCUM_MODE = Merge List Attributes
    ATTR_CONFLICT_RES_LOOKUP = INCOMING_IF_CONFLICT
    LIST_ATTR = suitability{}
    ATTR_CONFLICT_RES = Use List Attribute Values
    ELEMENTS -> BulkAttributeRenamer_4
BulkAttributeRenamer_4
    ATTRCHOICE_ACTION = NONPROTECTEDFME
    CASE_DISP = NO
    MODE_CHOICE = RENAME
    PATTERN_ACTION_DISP = STRINGREPLACE
    REPLACE_PATTERN = suitability_
    ATTRCHOICE = All Attributes
    -> AttributeCreator_12
Note: Assign classname (Suitability)
AttributeCreator_12
    ATTR_TABLE = SET_TO objectclass_name (varchar(15)) = Suitability
    -> FeatureMerger_7 [REQUESTOR]
FeatureMerger_7
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> AttributeRenamer_10
AttributeRenamer_10
    ATTR_TABLE = RENAME_SET_DEFAULT reason_codeSpace > reason_codespace
    KEEP_RENAMED_ONLY = no
    MISSING_INPUT_ATTRS = REMOVE
    -> Sorter_3
Sorter_3
    SORT_PARM = cityobject_id NATURAL ASCENDING reason NATURAL ASCENDING
    SORTED -> Counter_13
Note: SUITABILITY counter
Counter_13
    CNT_ATTR = id
    DOMAIN = @Value(table_name)
    SCOPE = Global
    START = 0
    -> AttributeRenamer_87
AttributeRenamer_87
    ATTR_TABLE = RENAME_SET_DEFAULT schedule_xlink_href > gml_link
    KEEP_RENAMED_ONLY = no
    MISSING_INPUT_ATTRS = REMOVE
    -> StringReplacer_37
Note: Trim # from XLinks
StringReplacer_37
    CASE = NO
    FIND_TEXT = #
    NO_MATCH = _FME_NO_OP_
    REGEXP = NO
    SRC_ATTRS = gml_link
    -> FeatureMerger_8 [REQUESTOR]
Note: Get schedule_id
FeatureMerger_8
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> FeatureWriter_45 [citydb.ng3_suitability]
    UNMERGED_REQUESTOR -> FeatureWriter_45 [citydb.ng3_suitability]
Note: Insert into ng3_SUITABILITY
FeatureWriter_45
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: CITYOBJECT RELATION
Junction_167
    -> FeatureMerger_102 [SUPPLIER]
    -> Junction_118
Junction_161
    -> AttributeKeeper_77
AttributeKeeper_77
    CREATE_BULK_MODE_FEATURES = NO
    KEEP_ATTRS = id
    KEEP_LIST = related_to{}
    -> ListExploder_16
ListExploder_16
    ATTR_ACCUM_MODE = Merge List Attributes
    ATTR_CONFLICT_RES_LOOKUP = INCOMING_IF_CONFLICT
    LIST_ATTR = related_to{}
    ATTR_CONFLICT_RES = Use List Attribute Values
    ELEMENTS -> BulkAttributeRenamer_82
BulkAttributeRenamer_82
    ATTRCHOICE_ACTION = NONPROTECTEDFME
    CASE_DISP = NO
    MODE_CHOICE = RENAME
    PATTERN_ACTION_DISP = STRINGREPLACE
    REPLACE_PATTERN = city_object_relation_
    ATTRCHOICE = All Attributes
    -> AttributeRenamer_62
AttributeRenamer_62
    ATTR_TABLE:
      RENAME_SET_DEFAULT id > ng3_cityobject_id
      RENAME_SET_DEFAULT relation_type_codeSpace > relation_type_codespace
      RENAME_SET_DEFAULT related_to_xlink_href > gml_link
    KEEP_RENAMED_ONLY = no
    MISSING_INPUT_ATTRS = REMOVE
    -> StringReplacer_50
Note: Trim # from XLinks
StringReplacer_50
    CASE = NO
    FIND_TEXT = #
    NO_MATCH = _FME_NO_OP_
    REGEXP = NO
    SRC_ATTRS = gml_link
    -> FeatureMerger_103 [REQUESTOR]
Junction_162
    -> AttributeKeeper_79
AttributeKeeper_79
    CREATE_BULK_MODE_FEATURES = NO
    KEEP_ATTRS = id,gmlid
    -> AttributeRenamer_47
AttributeRenamer_47
    ATTR_TABLE:
      RENAME_SET_DEFAULT id > cityobject_id
      RENAME_SET_DEFAULT gmlid > gml_link
    KEEP_RENAMED_ONLY = no
    MISSING_INPUT_ATTRS = REMOVE
    -> FeatureMerger_103 [SUPPLIER]
Note: Assign target cityobject_id
FeatureMerger_103
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeCreator_19
Note: Assign classname (CityObjectRelation)
AttributeCreator_19
    ATTR_TABLE = SET_TO objectclass_name (varchar(18)) = CityObjectRelation
    -> FeatureMerger_102 [REQUESTOR]
FeatureMerger_102
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter_34
Sorter_34
    SORT_PARM = ng3_cityobject_id NATURAL ASCENDING cityobject_id NATURAL ASCENDING relation_type NATURAL ASCENDING
    SORTED -> Counter_37
Note: Counter CITYOBJECT_RELATION
Counter_37
    CNT_ATTR = id
    DOMAIN = @Value(table_name)
    SCOPE = Global
    START = 0
    -> FeatureWriter_78 [citydb.ng3_ctyobj_relation]
Note: Insert into ng3_SUITABILITY
FeatureWriter_78
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: External Reference (for New CityObjects)
Note: Junction_117 : Output
Junction_118
    -> FeatureMerger_4 [SUPPLIER]
Junction_160
    -> AttributeKeeper_13
AttributeKeeper_13
    CREATE_BULK_MODE_FEATURES = NO
    KEEP_ATTRS = id
    KEEP_LIST = externalReference{}
    -> ListExploder_3
ListExploder_3
    ATTR_ACCUM_MODE = Merge List Attributes
    ATTR_CONFLICT_RES_LOOKUP = INCOMING_IF_CONFLICT
    LIST_ATTR = externalReference{}
    ATTR_CONFLICT_RES = Use List Attribute Values
    ELEMENTS -> AttributeRenamer_9
AttributeRenamer_9
    ATTR_TABLE:
      RENAME_SET_DEFAULT id > cityobject_id
      RENAME_SET_DEFAULT externalObject.name > name
      RENAME_SET_DEFAULT externalObject.uri > uri
      RENAME_SET_DEFAULT informationSystem > infosys
    KEEP_RENAMED_ONLY = no
    MISSING_INPUT_ATTRS = REMOVE
    -> AttributeCreator_9
Note: Assign classname (CityObjectRelation)
AttributeCreator_9
    ATTR_TABLE = SET_TO objectclass_name (varchar(18)) = ExternalReference
    -> FeatureMerger_4 [REQUESTOR]
FeatureMerger_4
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter_2
Sorter_2
    SORT_PARM = cityobject_id NATURAL ASCENDING
    SORTED -> Counter_2
Note: Counter EXTERNAL_REFERENCE
Counter_2
    CNT_ATTR = id
    DOMAIN = @Value(table_name)
    SCOPE = Global
    START = 0
    -> FeatureWriter_32 [citydb.external_reference]
Note: Insert into ng3_SUITABILITY
FeatureWriter_32
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: ng3_BUILDING
Note: Junction_46 : Output
Junction_56
    -> QualifiedAttributeWriter_4 [objectclass_name_list]
Junction_166
    -> GeometryRemover_2
GeometryRemover_2
    REMOVE_COORDSYS = No
    -> AttributeKeeper_47
Note: Keep only ADE Building attributes
AttributeKeeper_47
    CREATE_BULK_MODE_FEATURES = NO
    KEEP_ATTRS = gml_parent_id,objectclass_name,gmlid,id,objectclass_id,parent_id
    KEEP_LIST = bdg_attic_thermal_status{} bdg_basement_thermal_status{} bdg_construction_weight{} bdg_height{} bdg_is_protected{} bdg_type{} bdg_volume{} bdg_area{}
    -> BulkAttributeRenamer_50
Note: Bulk rename for buildings
BulkAttributeRenamer_50
    ATTRCHOICE_ACTION = NONPROTECTEDFME
    CASE_DISP = NO
    MODE_CHOICE = RENAME
    PATTERN_ACTION_DISP = STRINGREPLACE
    REPLACE_PATTERN = bdg_
    ATTRCHOICE = All Attributes
    -> ListExploder_9
ListExploder_9
    ATTR_ACCUM_MODE = Merge List Attributes
    ATTR_CONFLICT_RES_LOOKUP = INCOMING_IF_CONFLICT
    LIST_ATTR = attic_thermal_status{}
    ATTR_CONFLICT_RES = Use List Attribute Values
    ELEMENTS -> ListExploder_10
    <REJECTED> -> ListExploder_10
ListExploder_10
    ATTR_ACCUM_MODE = Merge List Attributes
    ATTR_CONFLICT_RES_LOOKUP = INCOMING_IF_CONFLICT
    LIST_ATTR = basement_thermal_status{}
    ATTR_CONFLICT_RES = Use List Attribute Values
    ELEMENTS -> ListExploder_11
    <REJECTED> -> ListExploder_11
ListExploder_11
    ATTR_ACCUM_MODE = Merge List Attributes
    ATTR_CONFLICT_RES_LOOKUP = INCOMING_IF_CONFLICT
    LIST_ATTR = is_protected{}
    ATTR_CONFLICT_RES = Use List Attribute Values
    ELEMENTS -> AttributeRenamer_92
    <REJECTED> -> AttributeRenamer_92
Note: Rename ADE _abstractBuilding attributes
AttributeRenamer_92
    ATTR_TABLE:
      RENAME_SET_DEFAULT type{0} > type
      RENAME_SET_DEFAULT type{0}.codeSpace > type_codespace
      RENAME_SET_DEFAULT construction_weight{0} > constr_weight
      RENAME_SET_DEFAULT construction_weight{0}.codeSpace > constr_weight_codespace
    KEEP_RENAMED_ONLY = no
    MISSING_INPUT_ATTRS = REMOVE
    -> AttributeRenamer_20
AttributeRenamer_20
    ATTR_TABLE:
      RENAME_SET_DEFAULT attic_thermal_status > attic_thm_status
      RENAME_SET_DEFAULT basement_thermal_status > basement_thm_status
    KEEP_RENAMED_ONLY = no
    MISSING_INPUT_ATTRS = REMOVE
    -> AttributeCreator_8
Note: boolean to numeric
AttributeCreator_8
    ATTR_TABLE = SET_TO is_protected (varchar(200)) = FME_CONDITIONAL:DEFAULT_VALUE'0'BOOL_OP;OR;COMPOSITE_TEST;1;TEST @Value(is_protected) = true'1'FME_NUM_CONDITIONS2___
    -> FeatureWriter_53 [citydb.ng3_building]
Note: Insert into ng3_BUILDING
FeatureWriter_53
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = Shared 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_building -> AttributeKeeper_54
    citydb.ng3_building -> QualifiedAttributeWriter_4 [CityObject]
QualifiedAttributeWriter_4
    ID = @Value(id)
    OBJECTCLASS_ID = @Value(objectclass_id)
    OBJECTCLASS_NAME = @Value(objectclass_name)
    TABLE_NAME = @Value(table_name)
    TABLE_NAME_2 = @Value(table_name)
    cp_citydb_schema = $(citydb_schema)
AttributeKeeper_54
    CREATE_BULK_MODE_FEATURES = NO
    KEEP_ATTRS = id,objectclass_name,gmlid
    -> Junction_147
    -> AttributeKeeper_3
AttributeKeeper_3
    CREATE_BULK_MODE_FEATURES = NO
    KEEP_ATTRS = gmlid,id
    -> Junction_110
    -> Junction_112
    -> Junction_114
Note: AttributeRenamer_4 : Input
Junction_110
    -> Junction_111
Note: AttributeRenamer_112 : Input
Junction_112
    -> Junction_113
Note: AttributeRenamer_74 : Input
Junction_114
    -> Junction_115
Note: AttributeFilter_4 : Input
Junction_147
    -> Junction_148

Bookmark: Building module
Junction_46
    -> CityObject_editor_3 [co_objectclass_name_list]
    -> CityObject_editor_4 [co_objectclass_name_list]
Junction_60
    -> CityObject_editor_6 [co_objectclass_name_list]
    -> CityObject_editor_5 [co_objectclass_name_list]
Junction_177
    -> CityObject_editor_12 [co_objectclass_name_list]
    -> CityObject_editor_13 [co_objectclass_name_list]
    -> CityObject_editor_14 [co_objectclass_name_list]
bldg_BuildingInstallation (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer
    -> Junction_191
bldg_IntBuildingInstallation (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer
    -> Junction_191
bldg_Room (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, citygml_interior_furniture{}.xlink_href xml_buffer, citygml_room_installation{}.xlink_href xml_buffer
    -> CityObject_editor_13 [CityObject]
bldg_BuildingFurniture (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer
    -> CityObject_editor_14 [CityObject]
bldg_Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, nrg3_bdg_area{}.nrg3_qualified_area_nrg3_description xml_buffer, nrg3_bdg_area{}.nrg3_qualified_area_nrg3_source xml_buffer, nrg3_bdg_area{}.nrg3_qualified_area_nrg3_value xml_real64, nrg3_bdg_area{}.nrg3_qualified_area_nrg3_value_units xml_buffer, nrg3_bdg_area{}.nrg3_qualified_area_nrg3_type xml_buffer, nrg3_bdg_area{}.nrg3_qualified_area_nrg3_type_codeSpace xml_buffer,
      nrg3_bdg_attic_thermal_status{} xml_char(24), nrg3_bdg_basement_thermal_status{} xml_char(24), nrg3_bdg_construction_weight{} xml_buffer, nrg3_bdg_construction_weight{}.codeSpace xml_buffer, nrg3_bdg_height{}.nrg3_qualified_height_nrg3_description xml_buffer, nrg3_bdg_height{}.nrg3_qualified_height_nrg3_source xml_buffer, nrg3_bdg_height{}.nrg3_qualified_height_nrg3_value xml_real64, nrg3_bdg_height{}.nrg3_qualified_height_nrg3_value_units xml_buffer, nrg3_bdg_height{}.nrg3_qualified_height_nrg3_type xml_buffer, nrg3_bdg_height{}.nrg3_qualified_height_nrg3_type_codeSpace xml_buffer, nrg3_bdg_is_protected{} xml_boolean, nrg3_bdg_type{} xml_buffer, nrg3_bdg_type{}.codeSpace xml_buffer, nrg3_bdg_volume{}.nrg3_qualified_volume_nrg3_description xml_buffer, nrg3_bdg_volume{}.nrg3_qualified_volume_nrg3_source xml_buffer, nrg3_bdg_volume{}.nrg3_qualified_volume_nrg3_value xml_real64, nrg3_bdg_volume{}.nrg3_qualified_volume_nrg3_value_units xml_buffer, nrg3_bdg_volume{}.nrg3_qualified_volume_nrg3_type xml_buffer, nrg3_bdg_volume{}.nrg3_qualified_volume_nrg3_type_codeSpace xml_buffer, nrg3_building_unit{}.xlink_href xml_buffer, nrg3_energy_performance_certificate{}.xlink_href xml_buffer, nrg3_refurbishment_measure{}.xlink_href xml_buffer, nrg3_thermal_zone{}.xlink_href xml_buffer, nrg3_usage_zone{}.xlink_href xml_buffer
    -> CityObject_editor_3 [CityObject]
bldg_BuildingPart (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, nrg3_bdg_area{}.nrg3_qualified_area_nrg3_description xml_buffer, nrg3_bdg_area{}.nrg3_qualified_area_nrg3_source xml_buffer, nrg3_bdg_area{}.nrg3_qualified_area_nrg3_value xml_real64, nrg3_bdg_area{}.nrg3_qualified_area_nrg3_value_units xml_buffer, nrg3_bdg_area{}.nrg3_qualified_area_nrg3_type xml_buffer, nrg3_bdg_area{}.nrg3_qualified_area_nrg3_type_codeSpace xml_buffer,
      nrg3_bdg_attic_thermal_status{} xml_char(24), nrg3_bdg_basement_thermal_status{} xml_char(24), nrg3_bdg_construction_weight{} xml_buffer, nrg3_bdg_construction_weight{}.codeSpace xml_buffer, nrg3_bdg_height{}.nrg3_qualified_height_nrg3_description xml_buffer, nrg3_bdg_height{}.nrg3_qualified_height_nrg3_source xml_buffer, nrg3_bdg_height{}.nrg3_qualified_height_nrg3_value xml_real64, nrg3_bdg_height{}.nrg3_qualified_height_nrg3_value_units xml_buffer, nrg3_bdg_height{}.nrg3_qualified_height_nrg3_type xml_buffer, nrg3_bdg_height{}.nrg3_qualified_height_nrg3_type_codeSpace xml_buffer, nrg3_bdg_is_protected{} xml_boolean, nrg3_bdg_type{} xml_buffer, nrg3_bdg_type{}.codeSpace xml_buffer, nrg3_bdg_volume{}.nrg3_qualified_volume_nrg3_description xml_buffer, nrg3_bdg_volume{}.nrg3_qualified_volume_nrg3_source xml_buffer, nrg3_bdg_volume{}.nrg3_qualified_volume_nrg3_value xml_real64, nrg3_bdg_volume{}.nrg3_qualified_volume_nrg3_value_units xml_buffer, nrg3_bdg_volume{}.nrg3_qualified_volume_nrg3_type xml_buffer, nrg3_bdg_volume{}.nrg3_qualified_volume_nrg3_type_codeSpace xml_buffer, nrg3_building_unit{}.xlink_href xml_buffer, nrg3_energy_performance_certificate{}.xlink_href xml_buffer, nrg3_refurbishment_measure{}.xlink_href xml_buffer, nrg3_thermal_zone{}.xlink_href xml_buffer, nrg3_usage_zone{}.xlink_href xml_buffer
    -> CityObject_editor_4 [CityObject]
bldg_GroundSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_WallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_RoofSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_OuterCeilingSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_OuterFloorSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_FloorSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_InteriorWallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_CeilingSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_ClosureSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      citygml_opening{}.xlink_href xml_buffer, nrg3_bdg_bdry_surf_azimuth{} xml_real64, nrg3_bdg_bdry_surf_azimuth{}.units xml_buffer, nrg3_bdg_bdry_surf_ground_view_factor{} xml_real64, nrg3_bdg_bdry_surf_ground_view_factor{}.units xml_buffer, nrg3_bdg_bdry_surf_heat_capacity{} xml_real64, nrg3_bdg_bdry_surf_heat_capacity{}.units xml_buffer, nrg3_bdg_bdry_surf_inclination{} xml_real64, nrg3_bdg_bdry_surf_inclination{}.units xml_buffer, nrg3_bdg_bdry_surf_is_adiabatic{} xml_boolean, nrg3_bdg_bdry_surf_opaque_surface_area{} xml_real64, nrg3_bdg_bdry_surf_opaque_surface_area{}.units xml_buffer, nrg3_bdg_bdry_surf_opening_to_surface_ratio{} xml_real64, nrg3_bdg_bdry_surf_opening_to_surface_ratio{}.units xml_buffer, nrg3_bdg_bdry_surf_sky_view_factor{} xml_real64, nrg3_bdg_bdry_surf_sky_view_factor{}.units xml_buffer, nrg3_bdg_bdry_surf_thickness{} xml_real64, nrg3_bdg_bdry_surf_thickness{}.units xml_buffer, nrg3_bdg_bdry_surf_total_surface_area{} xml_real64, nrg3_bdg_bdry_surf_total_surface_area{}.units xml_buffer
    -> Junction_189
bldg_Window (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      nrg3_bdg_opn_area{} xml_real64, nrg3_bdg_opn_area{}.units xml_buffer, nrg3_bdg_opn_azimuth{} xml_real64, nrg3_bdg_opn_azimuth{}.units xml_buffer, nrg3_bdg_opn_ground_view_factor{} xml_real64, nrg3_bdg_opn_ground_view_factor{}.units xml_buffer, nrg3_bdg_opn_inclination{} xml_real64, nrg3_bdg_opn_inclination{}.units xml_buffer, nrg3_bdg_opn_sky_view_factor{} xml_real64, nrg3_bdg_opn_sky_view_factor{}.units xml_buffer
    -> Junction_190
bldg_Door (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer,
      nrg3_bdg_opn_area{} xml_real64, nrg3_bdg_opn_area{}.units xml_buffer, nrg3_bdg_opn_azimuth{} xml_real64, nrg3_bdg_opn_azimuth{}.units xml_buffer, nrg3_bdg_opn_ground_view_factor{} xml_real64, nrg3_bdg_opn_ground_view_factor{}.units xml_buffer, nrg3_bdg_opn_inclination{} xml_real64, nrg3_bdg_opn_inclination{}.units xml_buffer, nrg3_bdg_opn_sky_view_factor{} xml_real64, nrg3_bdg_opn_sky_view_factor{}.units xml_buffer, citygml_address{}.xlink_href xml_buffer
    -> Junction_190

Bookmark: CityObjectGroup module
Junction_34
    -> CityObject_editor_2 [co_objectclass_name_list]
grp_CityObjectGroup (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_group_member{}.role xml_buffer, citygml_group_member{}.xlink_href xml_buffer, citygml_parent_xlink_href xml_buffer, citygml_level_of_detail{} xml_buffer
    -> CityObject_editor_2 [CityObject]

Bookmark: LandUse
Junction_198
    -> CityObject_editor_19 [co_objectclass_name_list]
luse_LandUse (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer
    -> CityObject_editor_19 [CityObject]

Bookmark: Relief module
Junction_51
    -> CityObject_editor_10 [co_objectclass_name_list]
    -> CityObject_editor_11 [co_objectclass_name_list]
    -> CityObject_editor_16 [co_objectclass_name_list]
    -> CityObject_editor_17 [co_objectclass_name_list]
    -> CityObject_editor_18 [co_objectclass_name_list]
dem_ReliefFeature (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_relief_component{}.xlink_href xml_buffer
    -> CityObject_editor_10 [CityObject]
dem_TINRelief (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer
    -> CityObject_editor_11 [CityObject]
dem_BreaklineRelief (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_level_of_detail{} xml_buffer
    -> CityObject_editor_16 [CityObject]
dem_MassPointRelief (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer
    -> CityObject_editor_17 [CityObject]
dem_RasterRelief (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer
    -> CityObject_editor_18 [CityObject]

Bookmark: CityFurniture
Junction_48
    -> CityObject_editor_7 [co_objectclass_name_list]
frn_CityFurniture (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer
    -> CityObject_editor_7 [CityObject]

Bookmark: Vegetation module
Junction_184
    -> CityObject_editor_9 [co_objectclass_name_list]
    -> CityObject_editor_8 [co_objectclass_name_list]
veg_SolitaryVegetationObject (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_species xml_buffer, citygml_species_codeSpace xml_buffer, citygml_height xml_real64, citygml_height_units xml_buffer, citygml_trunk_diameter xml_real64, citygml_trunk_diameter_units xml_buffer, citygml_crown_diameter xml_real64, citygml_crown_diameter_units xml_buffer, citygml_level_of_detail{} xml_buffer
    -> CityObject_editor_8 [CityObject]
veg_PlantCover (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_average_height xml_real64, citygml_average_height_units xml_buffer, citygml_level_of_detail{} xml_buffer
    -> CityObject_editor_9 [CityObject]

Bookmark: GenericCityObject
Junction_182
    -> CityObject_editor_15 [co_objectclass_name_list]
gen_GenericCityObject (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), nrg3_device{}.xlink_href xml_buffer, nrg3_layered_construction{}.xlink_href xml_buffer, nrg3_related_to{}.nrg3_city_object_relation_nrg3_relation_type xml_buffer, nrg3_related_to{}.nrg3_city_object_relation_nrg3_relation_type_codeSpace xml_buffer, nrg3_related_to{}.nrg3_city_object_relation_nrg3_related_to_xlink_href xml_buffer, nrg3_resource{}.xlink_href xml_buffer, nrg3_suitability{}.nrg3_suitability_nrg3_reason xml_buffer, nrg3_suitability{}.nrg3_suitability_nrg3_reason_codeSpace xml_buffer, nrg3_suitability{}.nrg3_suitability_nrg3_description xml_buffer, nrg3_suitability{}.nrg3_suitability_nrg3_value xml_real64, nrg3_suitability{}.nrg3_suitability_nrg3_value_units xml_buffer, nrg3_suitability{}.nrg3_suitability_nrg3_schedule_xlink_href xml_buffer, nrg3_utility_network_connection{}.xlink_href xml_buffer, nrg3_weather_data{}.xlink_href xml_buffer, citygml_appearance{}.xlink_href xml_buffer, citygml_class xml_buffer,
      citygml_class_codeSpace xml_buffer, citygml_function{} xml_buffer, citygml_function{}.codeSpace xml_buffer, citygml_usage{} xml_buffer, citygml_usage{}.codeSpace xml_buffer, citygml_level_of_detail{} xml_buffer
    -> CityObject_editor_15 [CityObject]

Bookmark: Address
Junction_154
    -> Feature_editor_3 [f_objectclass_name_list]
core_Address (reader CITYGML_2)
    attributes: citygml_target_uri xml_buffer, citygml_feature_role xml_buffer, citygml_feature_role_attr_name xml_buffer, citygml_feature_role_attr_val xml_buffer, gml_description xml_buffer, gml_name xml_buffer, citygml_address xml_xml
    -> Feature_editor_3

Bookmark: Appearance
Junction_152
    -> Feature_editor_2 [f_objectclass_name_list]
Junction_153
    -> Feature_editor [f_objectclass_name_list]
app_Appearance (reader CITYGML_2)
    attributes: citygml_target_uri xml_buffer, citygml_feature_role xml_buffer, citygml_feature_role_attr_name xml_buffer, citygml_feature_role_attr_val xml_buffer, gml_description xml_buffer, gml_name xml_buffer, citygml_surface_data_member{}.xlink_href xml_buffer
    -> Feature_editor_2
app_X3DMaterial (reader CITYGML_2)
    attributes: citygml_target_uri xml_buffer, citygml_feature_role xml_buffer, citygml_feature_role_attr_name xml_buffer, citygml_feature_role_attr_val xml_buffer, gml_description xml_buffer, gml_name xml_buffer, citygml_target{} xml_buffer
    -> Feature_editor

Bookmark: CITYOBJECTS (both new and existing)
Note: AttributeKeeper_51 : Output
Junction_119
    -> AttributeRenamer_7
Note: From ng3_layered_component writer
AttributeRenamer_7
    ATTR_TABLE:
      RENAME_SET_DEFAULT id > layered_construction_id
      RENAME_SET_DEFAULT gmlid > gml_link
    KEEP_RENAMED_ONLY = no
    MISSING_INPUT_ATTRS = REMOVE
    -> FeatureMerger_55 [SUPPLIER]
    -> FeatureMerger_3 [SUPPLIER]
AttributeKeeper_5
    CREATE_BULK_MODE_FEATURES = NO
    KEEP_ATTRS = gml_parent_id,gmlid,id,objectclass_id,objectclass_name
    KEEP_LIST = externalReference{} layered_construction{} related_to{} suitability{} citygml_generalizes_to{}
    -> ListExploder
    -> Junction_159
AttributeKeeper_7
    CREATE_BULK_MODE_FEATURES = NO
    KEEP_ATTRS = gml_parent_id,gmlid,id,objectclass_id,objectclass_name,parent_id
    KEEP_LIST = externalReference{} layered_construction{} related_to{} suitability{} utility_network_connection{}
    -> GeometryRemover_33
    -> AttributeKeeper_6
GeometryRemover_33
    REMOVE_COORDSYS = No
    -> FeatureMerger_134 [REQUESTOR]
AttributeKeeper_6
    CREATE_BULK_MODE_FEATURES = NO
    KEEP_ATTRS = id
    -> Deaggregator_9
Deaggregator_9
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    RECURSIVE = No
    SPLIT_COMPOSITES = No
    ATTR_CONFLICT_RES = Use List Attribute Values
    MODE = Flatten One Level
    DEAGGREGATED -> AttributeFilter_17
AttributeFilter_17
    ATTR_NAME = _geometry_name
    ATTR_VALUES = <Empty>,<Missing>,<Null>,<Unfiltered>,referencePoint
    referencePoint -> FeatureMerger_134 [SUPPLIER]
FeatureMerger_134
    JOIN_KEYS = @Value(id) @Value(id) AUTO
    MERGE_TYPE = Geometry
    PROCESS_DUPS = NO
    REJECT_NULL_MISSING_KEYS = No
    SUPPLIERS_FIRST = No
    MERGED -> ListExploder
    UNMERGED_REQUESTOR -> ListExploder
ListExploder
    ATTR_ACCUM_MODE = Prefix List Attributes
    INCOMING_PREFIX = layered_construction_
    LIST_ATTR = layered_construction{}
    ELEMENTS -> AttributeRenamer_52
    <REJECTED> -> AttributeRenamer_52
AttributeRenamer_52
    ATTR_TABLE = RENAME_SET_DEFAULT layered_construction_xlink_href > gml_link
    KEEP_RENAMED_ONLY = no
    MISSING_INPUT_ATTRS = REMOVE
    -> StringReplacer_22
Note: Trim # from XLinks
StringReplacer_22
    CASE = NO
    FIND_TEXT = #
    NO_MATCH = _FME_NO_OP_
    REGEXP = NO
    SRC_ATTRS = gml_link
    -> FeatureMerger_55 [REQUESTOR]
Note: Assign layered_construction_id
FeatureMerger_55
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes and Geometry
    PROCESS_DUPS = NO
    REJECT_NULL_MISSING_KEYS = No
    SUPPLIERS_FIRST = No
    ATTR_CONFLICT_RES = Use Requestor
    MERGED -> FeatureWriter_25 [citydb.ng3_cityobject]
    UNMERGED_REQUESTOR -> FeatureWriter_25 [citydb.ng3_cityobject]
Note: Insert into ng3_CITYOBJECT
FeatureWriter_25
    DATASET = Shared 3DCityDB connection
    DATASET_ATTR = _dataset
    FEATURE_TYPE_LIST_ATTR = _feature_types
    FORMAT = POSTGIS
    POSTGIS_BULK_COPY = YES
    POSTGIS_COORDINATE_SYSTEM_GRANULARITY = FEATURE
    POSTGIS_GENERIC_GEOMETRY = yes
    POSTGIS_LOWERCASE_ATTRIBUTE_NAMES = Yes
    POSTGIS_NAMED_CONNECTION = eade2_test.citydb @ localhost (pg16) AS postgres
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
    citydb.ng3_cityobject -> GeometryRemover_3
GeometryRemover_3
    REMOVE_COORDSYS = No
    -> Junction_168
Junction_168
    -> Junction_170
    -> Junction_161
    -> Junction_162
    -> AttributeKeeper_14
AttributeKeeper_14
    CREATE_BULK_MODE_FEATURES = NO
    KEEP_ATTRS = gmlid,id,objectclass_name
    -> Junction_135
    -> AttributeKeeper_10
AttributeKeeper_10
    CREATE_BULK_MODE_FEATURES = NO
    KEEP_ATTRS = gmlid,id
    -> Junction_134
    -> Junction_130
    -> Junction_150
Note: AttributeRenamer_76 : Input
Junction_134
    -> Junction_136
Note: AttributeRenamer_44 : Input
Junction_130
    -> Junction_131
Note: AttributeRenamer_48 : Input
Junction_150
    -> Junction_151
Note: Device follow autonomous path as they are second-level objects.
AttributeKeeper_9
    CREATE_BULK_MODE_FEATURES = NO
    KEEP_ATTRS = gml_parent_id,gmlid,id,objectclass_id,objectclass_name
    KEEP_LIST = externalReference{} layered_construction{} related_to{} suitability{} citygml_generalizes_to{}
    -> ListExploder_2
    -> Junction_159
ListExploder_2
    ATTR_ACCUM_MODE = Prefix List Attributes
    INCOMING_PREFIX = layered_construction_
    LIST_ATTR = layered_construction{}
    ELEMENTS -> AttributeRenamer_5
    <REJECTED> -> AttributeRenamer_5
AttributeRenamer_5
    ATTR_TABLE = RENAME_SET_DEFAULT layered_construction_xlink_href > gml_link
    KEEP_RENAMED_ONLY = no
    MISSING_INPUT_ATTRS = REMOVE
    -> StringReplacer_2
Note: Trim # from XLinks
StringReplacer_2
    CASE = NO
    FIND_TEXT = #
    NO_MATCH = _FME_NO_OP_
    REGEXP = NO
    SRC_ATTRS = gml_link
    -> FeatureMerger_3 [REQUESTOR]
Note: Assign layered_construction_id
FeatureMerger_3
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes and Geometry
    PROCESS_DUPS = NO
    REJECT_NULL_MISSING_KEYS = No
    SUPPLIERS_FIRST = No
    ATTR_CONFLICT_RES = Use Requestor
    MERGED -> FeatureWriter_26 [citydb.ng3_cityobject]
    UNMERGED_REQUESTOR -> FeatureWriter_26 [citydb.ng3_cityobject]
Note: Insert into ng3_CITYOBJECT
FeatureWriter_26
    DATASET = Shared 3DCityDB connection
    DATASET_ATTR = _dataset
    FEATURE_TYPE_LIST_ATTR = _feature_types
    FORMAT = POSTGIS
    POSTGIS_BULK_COPY = YES
    POSTGIS_COORDINATE_SYSTEM_GRANULARITY = FEATURE
    POSTGIS_GENERIC_GEOMETRY = yes
    POSTGIS_LOWERCASE_ATTRIBUTE_NAMES = Yes
    POSTGIS_NAMED_CONNECTION = eade2_test.citydb @ localhost (pg16) AS postgres
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
    citydb.ng3_cityobject -> GeometryRemover_7
GeometryRemover_7
    REMOVE_COORDSYS = No
    -> Junction_169
Junction_169
    -> Junction_170
    -> Junction_161
    -> Junction_162
Junction_159
    -> Junction_160

Bookmark: To be improved
Note: Add timezone
AttributeCreator_25
    ATTR_TABLE:
      SET_TO period_begin (buffer) = FME_CONDITIONAL:DEFAULT_VALUE'FME_NULL_VALUE'BOOL_OP;OR;COMPOSITE_TEST;1;TEST period_begin ATTRIBUTE_HAS_A_VALUE _FME_BLANK_STRING_'@TimeZoneSet(@Value(period_begin),local,auto)'FME_NUM_CONDITIONS2___
      SET_TO period_end (buffer) = FME_CONDITIONAL:DEFAULT_VALUE'FME_NULL_VALUE'BOOL_OP;OR;COMPOSITE_TEST;1;TEST period_end ATTRIBUTE_HAS_A_VALUE _FME_BLANK_STRING_'@TimeZoneSet(@Value(period_end),local,auto)'FME_NUM_CONDITIONS2___
    -> DateTimeConverter
DateTimeConverter
    DATETIME_ATTR = period_begin period_end
    OUT_FORMAT = %Y-%m-%dT%H:%M:%S%Ez
    PASSTHROUGH = NO
    REPAIR_INPUT = NO
    -> FeatureWriter_13 [citydb.cityobject]
    <REJECTED> -> FeatureWriter_13 [citydb.cityobject]

Bookmark: SurfaceGeometryWriter
GeometryRemover_23
    REMOVE_COORDSYS = No
    -> FeatureMerger_118 [REQUESTOR]
SurfaceGeometryWriter_6
    ID = @Value(id)
    _GEOMETRY_NAME = @Value(_geometry_name)
    cp_citydb_schema = $(citydb_schema)
    sg_ids -> AttributeRenamer_136
    sg_gml_ids -> Junction_8
AttributeRenamer_136
    ATTR_TABLE = RENAME_SET_DEFAULT sg_id > brep_id
    KEEP_RENAMED_ONLY = no
    MISSING_INPUT_ATTRS = REMOVE
    -> FeatureMerger_118 [SUPPLIER]
FeatureMerger_118
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_119 [SUPPLIER]
    UNMERGED_REQUESTOR -> FeatureMerger_119 [SUPPLIER]
Junction_8
    -> Junction_3

Bookmark: GROUP TO CITYOBJECT
AttributeFilter_9
    ATTR_NAME = co_parent_id
    ATTR_VALUES = <Empty>,<Missing>,<Null>,<Unfiltered>
    <UNFILTERED> -> AttributeKeeper_43
AttributeKeeper_43
    CREATE_BULK_MODE_FEATURES = NO
    KEEP_ATTRS = co_parent_id,id
    -> AttributeRenamer_72
AttributeRenamer_72
    ATTR_TABLE:
      RENAME_SET_DEFAULT co_parent_id > cityobjectgroup_id
      RENAME_SET_DEFAULT id > cityobject_id
    KEEP_RENAMED_ONLY = no
    MISSING_INPUT_ATTRS = REMOVE
    -> FeatureWriter_42 [citydb.group_to_cityobject]
Note: Insert into GROUP_TO_CITYOBJECT
FeatureWriter_42
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: Write in table TEXTUREPARAM
Junction_9
    -> FeatureMerger_138 [REQUESTOR]
Junction_3
    -> FeatureMerger_138 [SUPPLIER]
FeatureMerger_138
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> AttributeManager_49
AttributeManager_49
    ATTR_TABLE:
      REMOVE gml_link (buffer)
      RENAME_SET_VALUE sg_id > surface_geometry_id (int64)
      SET_TO is_texture_parametrization (uint8) = 0
      REMOVE cityobject_id (int64)
    -> Sorter_36
Sorter_36
    SORT_PARM = surface_data_id NATURAL ASCENDING surface_geometry_id NATURAL ASCENDING
    SORTED -> FeatureWriter_56 [citydb.textureparam]
FeatureWriter_56
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: ng3_ADDRESS_TO_BUILDING_UNIT
Junction_156
    -> AttributeRenamer_27
AttributeRenamer_27
    ATTR_TABLE = RENAME_SET_DEFAULT gmlid > gml_link
    KEEP_RENAMED_ONLY = no
    MISSING_INPUT_ATTRS = REMOVE
    -> FeatureMerger_101 [SUPPLIER]
AttributeKeeper_72
    CREATE_BULK_MODE_FEATURES = NO
    KEEP_ATTRS = id
    KEEP_LIST = address{}.xlink_href
    -> ListExploder_15
ListExploder_15
    ATTR_ACCUM_MODE = Merge List Attributes
    ATTR_CONFLICT_RES_LOOKUP = INCOMING_IF_CONFLICT
    LIST_ATTR = address{}
    ATTR_CONFLICT_RES = Use List Attribute Values
    ELEMENTS -> AttributeRenamer_130
AttributeRenamer_130
    ATTR_TABLE:
      RENAME_SET_DEFAULT id > building_unit_id
      RENAME_SET_DEFAULT xlink_href > gml_link
    KEEP_RENAMED_ONLY = no
    MISSING_INPUT_ATTRS = REMOVE
    -> StringReplacer_49
Note: Trim # from XLinks
StringReplacer_49
    CASE = NO
    FIND_TEXT = #
    NO_MATCH = _FME_NO_OP_
    REGEXP = NO
    SRC_ATTRS = gml_link
    -> FeatureMerger_101 [REQUESTOR]
FeatureMerger_101
    ATTR_ACCUM_MODE = Merge Supplier
    ATTR_CONFLICT_RES_LOOKUP = REQUESTOR_IF_CONFLICT
    IGNORE_NULLS = No
    JOIN_KEYS = @Value(gml_link) @Value(gml_link) AUTO
    MERGE_TYPE = Attributes Only
    PROCESS_DUPS = NO
    REJECT_NULL_MISSING_KEYS = No
    SUPPLIERS_FIRST = No
    ATTR_CONFLICT_RES = Use Requestor
    MERGED -> Sorter_33
Sorter_33
    SORT_PARM = building_unit_id NATURAL ASCENDING address_id NATURAL ASCENDING
    SORTED -> FeatureWriter_77 [citydb.ng3_address_to_building_unit]
Note: Insert into ng3_ADDRESS_TO_BUILDING_UNIT
FeatureWriter_77
    COORDSYS = EPSG:28992
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: New Bookmark
AttributeCreator_17 [off]
    ATTR_TABLE:
      SET_TO gml_parent_id (buffer) = FME_NULL_VALUE
      SET_TO cityobject_id (varchar(14)) = FME_NULL_VALUE
    -> AttributeCreator_44

Bookmark: SurfaceGeometryWriter
SurfaceGeometryWriter
    ID = @Value(id)
    _GEOMETRY_NAME = @Value(_geometry_name)
    cp_citydb_schema = $(citydb_schema)
    sg_ids -> AttributeRenamer_98
    sg_gml_ids -> Junction_6
AttributeRenamer_98
    ATTR_TABLE = RENAME_SET_DEFAULT sg_id > lod1_solid_id
    KEEP_RENAMED_ONLY = no
    MISSING_INPUT_ATTRS = REMOVE
    -> FeatureMerger_111 [SUPPLIER]
SurfaceGeometryWriter_2
    ID = @Value(id)
    _GEOMETRY_NAME = @Value(_geometry_name)
    cp_citydb_schema = $(citydb_schema)
    sg_ids -> AttributeRenamer_138
    sg_gml_ids -> Junction_6
AttributeRenamer_138
    ATTR_TABLE = RENAME_SET_DEFAULT sg_id > lod2_solid_id
    KEEP_RENAMED_ONLY = no
    MISSING_INPUT_ATTRS = REMOVE
    -> FeatureMerger_112 [SUPPLIER]
SurfaceGeometryWriter_3
    ID = @Value(id)
    _GEOMETRY_NAME = @Value(_geometry_name)
    cp_citydb_schema = $(citydb_schema)
    sg_ids -> AttributeRenamer_140
    sg_gml_ids -> Junction_6
AttributeRenamer_140
    ATTR_TABLE = RENAME_SET_DEFAULT sg_id > lod3_solid_id
    KEEP_RENAMED_ONLY = no
    MISSING_INPUT_ATTRS = REMOVE
    -> FeatureMerger_113 [SUPPLIER]
Junction_6
    -> Junction_3
GeometryRemover_19
    REMOVE_COORDSYS = No
    -> FeatureMerger_111 [REQUESTOR]
FeatureMerger_111
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_112 [REQUESTOR]
    UNMERGED_REQUESTOR -> FeatureMerger_112 [REQUESTOR]
FeatureMerger_112
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_113 [REQUESTOR]
    UNMERGED_REQUESTOR -> FeatureMerger_113 [REQUESTOR]
FeatureMerger_113
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_110 [SUPPLIER]
    UNMERGED_REQUESTOR -> FeatureMerger_110 [SUPPLIER]

Bookmark: New Bookmark
AttributeCreator_40 [off]
    ATTR_TABLE:
      SET_TO gml_parent_id (buffer) = FME_NULL_VALUE
      SET_TO cityobject_id (varchar(14)) = FME_NULL_VALUE
    -> FeatureMerger_96 [REQUESTOR]

Bookmark: SurfaceGeometryWriter
GeometryRemover_31
    REMOVE_COORDSYS = No
    -> FeatureMerger_127 [REQUESTOR]
SurfaceGeometryWriter_9
    ID = @Value(id)
    _GEOMETRY_NAME = @Value(_geometry_name)
    cp_citydb_schema = $(citydb_schema)
    sg_ids -> AttributeRenamer_141
    sg_gml_ids -> Junction_2
AttributeRenamer_141
    ATTR_TABLE = RENAME_SET_DEFAULT sg_id > lod1_solid_id
    KEEP_RENAMED_ONLY = no
    MISSING_INPUT_ATTRS = REMOVE
    -> FeatureMerger_127 [SUPPLIER]
FeatureMerger_127
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_128 [REQUESTOR]
    UNMERGED_REQUESTOR -> FeatureMerger_128 [REQUESTOR]
SurfaceGeometryWriter_11
    ID = @Value(id)
    _GEOMETRY_NAME = @Value(_geometry_name)
    cp_citydb_schema = $(citydb_schema)
    sg_ids -> AttributeRenamer_143
    sg_gml_ids -> Junction_2
AttributeRenamer_143
    ATTR_TABLE = RENAME_SET_DEFAULT sg_id > lod2_solid_id
    KEEP_RENAMED_ONLY = no
    MISSING_INPUT_ATTRS = REMOVE
    -> FeatureMerger_128 [SUPPLIER]
FeatureMerger_128
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_129 [REQUESTOR]
    UNMERGED_REQUESTOR -> FeatureMerger_129 [REQUESTOR]
SurfaceGeometryWriter_12
    ID = @Value(id)
    _GEOMETRY_NAME = @Value(_geometry_name)
    cp_citydb_schema = $(citydb_schema)
    sg_ids -> AttributeRenamer_144
    sg_gml_ids -> Junction_2
AttributeRenamer_144
    ATTR_TABLE = RENAME_SET_DEFAULT sg_id > lod3_solid_id
    KEEP_RENAMED_ONLY = no
    MISSING_INPUT_ATTRS = REMOVE
    -> FeatureMerger_129 [SUPPLIER]
FeatureMerger_129
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_95 [SUPPLIER]
    UNMERGED_REQUESTOR -> FeatureMerger_95 [SUPPLIER]
Junction_2
    -> Junction_3

Bookmark: New Bookmark
AttributeCreator_41 [off]
    ATTR_TABLE:
      SET_TO gml_parent_id (buffer) = FME_NULL_VALUE
      SET_TO cityobject_id (varchar(14)) = FME_NULL_VALUE
    -> FeatureMerger_97 [REQUESTOR]

Bookmark: SurfaceGeometryWriter
SurfaceGeometryWriter_13
    ID = @Value(id)
    _GEOMETRY_NAME = @Value(_geometry_name)
    cp_citydb_schema = $(citydb_schema)
    sg_ids -> AttributeRenamer_145
    sg_gml_ids -> Junction
AttributeRenamer_145
    ATTR_TABLE = RENAME_SET_DEFAULT sg_id > lod1_solid_id
    KEEP_RENAMED_ONLY = no
    MISSING_INPUT_ATTRS = REMOVE
    -> FeatureMerger_131 [SUPPLIER]
SurfaceGeometryWriter_14
    ID = @Value(id)
    _GEOMETRY_NAME = @Value(_geometry_name)
    cp_citydb_schema = $(citydb_schema)
    sg_ids -> AttributeRenamer_146
    sg_gml_ids -> Junction
AttributeRenamer_146
    ATTR_TABLE = RENAME_SET_DEFAULT sg_id > lod2_solid_id
    KEEP_RENAMED_ONLY = no
    MISSING_INPUT_ATTRS = REMOVE
    -> FeatureMerger_132 [SUPPLIER]
SurfaceGeometryWriter_15
    ID = @Value(id)
    _GEOMETRY_NAME = @Value(_geometry_name)
    cp_citydb_schema = $(citydb_schema)
    sg_ids -> AttributeRenamer_147
    sg_gml_ids -> Junction
AttributeRenamer_147
    ATTR_TABLE = RENAME_SET_DEFAULT sg_id > lod3_solid_id
    KEEP_RENAMED_ONLY = no
    MISSING_INPUT_ATTRS = REMOVE
    -> FeatureMerger_133 [SUPPLIER]
Junction
    -> Junction_3
GeometryRemover_10
    REMOVE_COORDSYS = No
    -> FeatureMerger_131 [REQUESTOR]
FeatureMerger_131
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_132 [REQUESTOR]
    UNMERGED_REQUESTOR -> FeatureMerger_132 [REQUESTOR]
FeatureMerger_132
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_133 [REQUESTOR]
    UNMERGED_REQUESTOR -> FeatureMerger_133 [REQUESTOR]
FeatureMerger_133
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_98 [SUPPLIER]
    UNMERGED_REQUESTOR -> FeatureMerger_98 [SUPPLIER]

Bookmark: New Bookmark
AttributeCreator_7 [off]
    ATTR_TABLE:
      SET_TO gml_parent_id (buffer) = FME_NULL_VALUE
      SET_TO cityobject_id (varchar(14)) = FME_NULL_VALUE
    -> AttributeRenamer_133

Bookmark: New Bookmark
AttributeCreator_18 [off]
    ATTR_TABLE:
      SET_TO gml_parent_id (buffer) = FME_NULL_VALUE
      SET_TO cityobject_id (varchar(14)) = FME_NULL_VALUE
    -> Junction_137

Bookmark: New Bookmark
Note: Add timezone
AttributeCreator_33
    ATTR_TABLE:
      SET_TO start_date (buffer) = FME_CONDITIONAL:DEFAULT_VALUE'FME_NULL_VALUE'BOOL_OP;OR;COMPOSITE_TEST;1;TEST start_date ATTRIBUTE_HAS_A_VALUE _FME_BLANK_STRING_'@TimeZoneSet(@Value(start_date),local,auto)'FME_NUM_CONDITIONS2___
      SET_TO end_date (buffer) = FME_CONDITIONAL:DEFAULT_VALUE'FME_NULL_VALUE'BOOL_OP;OR;COMPOSITE_TEST;1;TEST end_date ATTRIBUTE_HAS_A_VALUE _FME_BLANK_STRING_'@TimeZoneSet(@Value(end_date),local,auto)'FME_NUM_CONDITIONS2___
    -> DateTimeConverter_2
DateTimeConverter_2
    DATETIME_ATTR = end_date start_date
    OUT_FORMAT = %Y-%m-%dT%H:%M:%S%Ez
    PASSTHROUGH = NO
    REPAIR_INPUT = NO
    -> FeatureWriter_48 [citydb.cityobject]
    <REJECTED> -> FeatureWriter_48 [citydb.cityobject]

Bookmark: New Bookmark
Note: Add timezone
AttributeCreator_52
    ATTR_TABLE:
      SET_TO issue_date (buffer) = FME_CONDITIONAL:DEFAULT_VALUE'FME_NULL_VALUE'BOOL_OP;OR;COMPOSITE_TEST;1;TEST issue_date ATTRIBUTE_HAS_A_VALUE _FME_BLANK_STRING_'@TimeZoneSet(@Value(issue_date),local,auto)'FME_NUM_CONDITIONS2___
      SET_TO expiration_date (buffer) = FME_CONDITIONAL:DEFAULT_VALUE'_FME_NO_OP_'BOOL_OP;OR;COMPOSITE_TEST;1;TEST expiration_date ATTRIBUTE_HAS_A_VALUE _FME_BLANK_STRING_'@TimeZoneSet(@Value(expiration_date),local,auto)'FME_NUM_CONDITIONS2___
    -> DateTimeConverter_3
DateTimeConverter_3
    DATETIME_ATTR = expiration_date issue_date
    OUT_FORMAT = %Y-%m-%dT%H:%M:%S%Ez
    PASSTHROUGH = NO
    REPAIR_INPUT = NO
    -> FeatureWriter_49 [citydb.cityobject]

Bookmark: New Bookmark
AttributeCreator_26 [off]
    ATTR_TABLE:
      SET_TO gml_parent_id (buffer) = FME_NULL_VALUE
      SET_TO cityobject_id (varchar(14)) = FME_NULL_VALUE
    -> Junction_138

Bookmark: SurfaceGeometryWriter
SurfaceGeometryWriter_4
    ID = @Value(id)
    _GEOMETRY_NAME = @Value(_geometry_name)
    cp_citydb_schema = $(citydb_schema)
    sg_ids -> AttributeRenamer_84
    sg_gml_ids -> Junction_5
AttributeRenamer_84
    ATTR_TABLE = RENAME_SET_DEFAULT sg_id > lod2_multi_surface_id
    KEEP_RENAMED_ONLY = no
    MISSING_INPUT_ATTRS = REMOVE
    -> FeatureMerger_115 [SUPPLIER]
SurfaceGeometryWriter_5
    ID = @Value(id)
    _GEOMETRY_NAME = @Value(_geometry_name)
    cp_citydb_schema = $(citydb_schema)
    sg_ids -> AttributeRenamer_113
    sg_gml_ids -> Junction_5
AttributeRenamer_113
    ATTR_TABLE = RENAME_SET_DEFAULT sg_id > lod3_multi_surface_id
    KEEP_RENAMED_ONLY = no
    MISSING_INPUT_ATTRS = REMOVE
    -> FeatureMerger_116 [SUPPLIER]
Junction_5
    -> Junction_3
AttributeKeeper_84
    CREATE_BULK_MODE_FEATURES = NO
    KEEP_ATTRS = id
    -> GeometryRemover_16
GeometryRemover_16
    REMOVE_COORDSYS = No
    -> FeatureMerger_115 [REQUESTOR]
FeatureMerger_115
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_116 [REQUESTOR]
    UNMERGED_REQUESTOR -> FeatureMerger_116 [REQUESTOR]
FeatureMerger_116
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_117 [SUPPLIER]
    UNMERGED_REQUESTOR -> FeatureMerger_117 [SUPPLIER]

Bookmark: Insert into ng3_THEM_SURFTO_THERMAL_ZONE
AttributeKeeper_61
    CREATE_BULK_MODE_FEATURES = NO
    KEEP_ATTRS = id,thermal_zone_id
    -> AttributeRenamer_111
AttributeRenamer_111
    ATTR_TABLE = RENAME_SET_DEFAULT id > thematic_surface_id
    KEEP_RENAMED_ONLY = no
    MISSING_INPUT_ATTRS = REMOVE
    -> Sorter_27
Sorter_27
    SORT_PARM = thermal_zone_id NUMERIC ASCENDING thematic_surface_id NUMERIC ASCENDING
    SORTED -> FeatureWriter_63 [citydb.ng3_them_surf_to_thermal_zone]
Note: Insert into ng3_THEM_SURFTO_THERMAL_ZONE
FeatureWriter_63
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: ng3_THEMATIC_SURFACE
GeometryRemover_4
    REMOVE_COORDSYS = No
    -> AttributeKeeper_50
Note: Keep attributes of ADE thematicsurface attributes
AttributeKeeper_50
    CREATE_BULK_MODE_FEATURES = NO
    KEEP_ATTRS = gml_parent_id,objectclass_name,gmlid,id,objectclass_id,parent_id
    KEEP_LIST = bdg_bdry_surf_azimuth{} bdg_bdry_surf_ground_view_factor{} bdg_bdry_surf_heat_capacity{} bdg_bdry_surf_inclination{} bdg_bdry_surf_is_adiabatic{} bdg_bdry_surf_opaque_surface_area{} bdg_bdry_surf_sky_view_factor{} bdg_bdry_surf_total_surface_area{}
    -> BulkAttributeRenamer_54
Note: Bulk rename for ThematicSurfaces
BulkAttributeRenamer_54
    ATTRCHOICE_ACTION = NONPROTECTEDFME
    CASE_DISP = NO
    MODE_CHOICE = RENAME
    PATTERN_ACTION_DISP = STRINGREPLACE
    REPLACE_PATTERN = bdg_bdry_surf_
    ATTRCHOICE = All Attributes
    -> ListExploder_8
ListExploder_8
    ATTR_ACCUM_MODE = Merge List Attributes
    ATTR_CONFLICT_RES_LOOKUP = INCOMING_IF_CONFLICT
    LIST_ATTR = is_adiabatic{}
    ATTR_CONFLICT_RES = Use List Attribute Values
    ELEMENTS -> AttributeRenamer_96
    <REJECTED> -> AttributeRenamer_96
Note: Rename ADE _ThematicSurface attributes
AttributeRenamer_96
    ATTR_TABLE:
      RENAME_SET_DEFAULT azimuth{0} > azimuth
      RENAME_SET_DEFAULT azimuth{0}.units > azimuth_uom
      RENAME_SET_DEFAULT ground_view_factor{0} > ground_view_factor
      RENAME_SET_DEFAULT ground_view_factor{0}.units > ground_view_factor_uom
      RENAME_SET_DEFAULT heat_capacity{0} > heat_capacity
      RENAME_SET_DEFAULT heat_capacity{0}.units > heat_capacity_uom
      RENAME_SET_DEFAULT inclination{0} > inclination
      RENAME_SET_DEFAULT inclination{0}.units > inclination_uom
      RENAME_SET_DEFAULT opaque_surface_area{0} > opaque_surf_area
      RENAME_SET_DEFAULT opaque_surface_area{0}.units > opaque_surf_area_uom
      RENAME_SET_DEFAULT opening_to_surface_ratio{0} > open_to_surf_ratio
      RENAME_SET_DEFAULT opening_to_surface_ratio{0}.units > open_to_surf_ratio_uom
      RENAME_SET_DEFAULT sky_view_factor{0} > sky_view_factor
      RENAME_SET_DEFAULT sky_view_factor{0}.units > sky_view_factor_uom
      RENAME_SET_DEFAULT thickness{0} > thickness
      RENAME_SET_DEFAULT thickness{0}.units > thickness_uom
      RENAME_SET_DEFAULT total_surface_area{0} > total_surf_area
      RENAME_SET_DEFAULT total_surface_area{0}.units > total_surf_area_uom
    KEEP_RENAMED_ONLY = no
    MISSING_INPUT_ATTRS = REMOVE
    -> AttributeCreator_20
Note: boolean to numeric
AttributeCreator_20
    ATTR_TABLE = SET_TO is_adiabatic (logical) = FME_CONDITIONAL:DEFAULT_VALUE'0'BOOL_OP;OR;COMPOSITE_TEST;1;TEST @Value(is_adiabatic) = true'1'FME_NUM_CONDITIONS2___
    -> FeatureWriter_54 [citydb.ng3_thematic_surface]
Note: Insert into ng3_THEMATIC_SURFACE
FeatureWriter_54
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: New CityObjects
Junction_100
    -> AttributeKeeper_5

Bookmark: SurfaceGeometryWriter
SurfaceGeometryWriter_10
    ID = @Value(id)
    _GEOMETRY_NAME = @Value(_geometry_name)
    cp_citydb_schema = $(citydb_schema)
    sg_ids -> AttributeRenamer_142
    sg_gml_ids -> Junction_4
AttributeRenamer_142
    ATTR_TABLE = RENAME_SET_DEFAULT sg_id > lod3_multi_surface_id
    KEEP_RENAMED_ONLY = no
    MISSING_INPUT_ATTRS = REMOVE
    -> FeatureMerger_125 [SUPPLIER]
Junction_4
    -> Junction_3
AttributeKeeper_63
    CREATE_BULK_MODE_FEATURES = NO
    KEEP_ATTRS = id
    -> GeometryRemover_30
GeometryRemover_30
    REMOVE_COORDSYS = No
    -> FeatureMerger_125 [REQUESTOR]
FeatureMerger_125
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_91 [SUPPLIER]
    UNMERGED_REQUESTOR -> FeatureMerger_91 [SUPPLIER]

Bookmark: ng3_OPENING_TO_THEATIC_SURFACE
AttributeKeeper_64
    CREATE_BULK_MODE_FEATURES = NO
    KEEP_ATTRS = id,thematic_surface_id
    -> AttributeRenamer_118
AttributeRenamer_118
    ATTR_TABLE = RENAME_SET_DEFAULT id > opening_id
    KEEP_RENAMED_ONLY = no
    MISSING_INPUT_ATTRS = REMOVE
    -> Sorter_32
Sorter_32
    SORT_PARM = thematic_surface_id NATURAL ASCENDING opening_id NATURAL ASCENDING
    SORTED -> FeatureWriter_69 [citydb.opening_to_them_surface]
Note: Insert into OPENING_TO_THEM_SURF
FeatureWriter_69
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: NR3_OPENING
GeometryRemover_5
    REMOVE_COORDSYS = No
    -> AttributeKeeper_52
Note: Keep only ADE Openings attributes
AttributeKeeper_52
    CREATE_BULK_MODE_FEATURES = NO
    KEEP_ATTRS = gml_parent_id,gmlid,id,parent_id
    KEEP_LIST = bdg_opn_area{} bdg_opn_azimuth{} bdg_opn_ground_view_factor{} bdg_opn_inclination{} bdg_opn_sky_view_factor{}
    -> BulkAttributeRenamer_57
Note: Bulk rename for Openings
BulkAttributeRenamer_57
    ATTRCHOICE_ACTION = NONPROTECTEDFME
    CASE_DISP = NO
    MODE_CHOICE = RENAME
    PATTERN_ACTION_DISP = STRINGREPLACE
    REPLACE_PATTERN = bdg_opn_
    ATTRCHOICE = All Attributes
    -> AttributeRenamer_99
Note: Rename ADE _Openings
AttributeRenamer_99
    ATTR_TABLE:
      RENAME_SET_DEFAULT co_id > id
      RENAME_SET_DEFAULT area{0} > area
      RENAME_SET_DEFAULT area{0}.units > area_uom
      RENAME_SET_DEFAULT azimuth{0} > azimuth
      RENAME_SET_DEFAULT azimuth{0}.units > azimuth_uom
      RENAME_SET_DEFAULT inclination{0} > inclination
      RENAME_SET_DEFAULT inclination{0}.units > inclination_uom
      RENAME_SET_DEFAULT ground_view_factor{0} > ground_view_factor
      RENAME_SET_DEFAULT ground_view_factor{0}.units > ground_view_factor_uom
      RENAME_SET_DEFAULT sky_view_factor{0} > sky_view_factor
      RENAME_SET_DEFAULT sky_view_factor{0}.units > sky_view_factor_uom
    KEEP_RENAMED_ONLY = no
    MISSING_INPUT_ATTRS = REMOVE
    -> FeatureWriter_55 [citydb.ng3_opening]
Note: Insert into ng3_OPENING
FeatureWriter_55
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = eade2_test.citydb @ localhost (pg16) AS postgres
    POSTGRES_START_TRANSACTION = 0
    POSTGRES_STRICT_TEMPORAL_TYPE_HANDLING = Yes
    POSTGRES_TRANSACTION_INTERVAL = 1000
    TOTAL_FEATURES_WRITTEN_ATTR = _total_features_written

Bookmark: Existing CityObjects
Junction_116
    -> AttributeKeeper_7

Bookmark: New Bookmark
AttributeCreator_37 [off]
    ATTR_TABLE:
      SET_TO gml_parent_id (buffer) = FME_NULL_VALUE
      SET_TO cityobject_id (varchar(14)) = FME_NULL_VALUE
    -> AttributeManager_25

Bookmark: New Bookmark
AttributeCreator_36 [off]
    ATTR_TABLE:
      SET_TO gml_parent_id (buffer) = FME_NULL_VALUE
      SET_TO cityobject_id (varchar(14)) = FME_NULL_VALUE
    -> AttributeManager_29

Bookmark: New Bookmark
AttributeCreator_15 [off]
    ATTR_TABLE:
      SET_TO gml_parent_id (buffer) = FME_NULL_VALUE
      SET_TO cityobject_id (varchar(14)) = FME_NULL_VALUE
    -> AttributeManager_32

Bookmark: Devices
Junction_149
    -> AttributeKeeper_9

Bookmark: SurfaceGeometryWriter
SurfaceGeometryWriter_7
    ID = @Value(id)
    _GEOMETRY_NAME = @Value(_geometry_name)
    cp_citydb_schema = $(citydb_schema)
    sg_ids -> AttributeRenamer_137
    sg_gml_ids -> Junction_7
AttributeRenamer_137
    ATTR_TABLE = RENAME_SET_DEFAULT sg_id > lod2_multi_surface_id
    KEEP_RENAMED_ONLY = no
    MISSING_INPUT_ATTRS = REMOVE
    -> FeatureMerger_121 [SUPPLIER]
SurfaceGeometryWriter_8
    ID = @Value(id)
    _GEOMETRY_NAME = @Value(_geometry_name)
    cp_citydb_schema = $(citydb_schema)
    sg_ids -> AttributeRenamer_139
    sg_gml_ids -> Junction_7
AttributeRenamer_139
    ATTR_TABLE = RENAME_SET_DEFAULT sg_id > lod3_multi_surface_id
    KEEP_RENAMED_ONLY = no
    MISSING_INPUT_ATTRS = REMOVE
    -> FeatureMerger_122 [SUPPLIER]
Junction_7
    -> Junction_3
GeometryRemover_27
    REMOVE_COORDSYS = No
    -> FeatureMerger_121 [REQUESTOR]
FeatureMerger_121
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_122 [REQUESTOR]
    UNMERGED_REQUESTOR -> FeatureMerger_122 [REQUESTOR]
FeatureMerger_122
    ATTR_ACCUM_MODE = Merge Supplier
    ATTR_CONFLICT_RES_LOOKUP = REQUESTOR_IF_CONFLICT
    IGNORE_NULLS = No
    JOIN_KEYS = @Value(id) @Value(id) AUTO
    MERGE_TYPE = Attributes Only
    PROCESS_DUPS = NO
    REJECT_NULL_MISSING_KEYS = No
    SUPPLIERS_FIRST = No
    ATTR_CONFLICT_RES = Use Requestor
    MERGED -> FeatureMerger_124 [SUPPLIER]
    UNMERGED_REQUESTOR -> FeatureMerger_124 [SUPPLIER]

Bookmark: New Bookmark
AttributeCreator_48 [off]
    ATTR_TABLE:
      SET_TO gml_parent_id (buffer) = FME_NULL_VALUE
      SET_TO cityobject_id (varchar(14)) = FME_NULL_VALUE
    -> AttributeRenamer_64

Bookmark: Update Xlinks after the new data has been added
Junction_158
    -> AttributeKeeper_85
AttributeKeeper_85
    CREATE_BULK_MODE_FEATURES = NO
    -> Aggregator_2
Note: Wait till all geometries have been written to the surface_geometry table before updating for is_xlink
Aggregator_2
    ACCUM_ATTRS_NAME = Drop Incoming Attributes
    AGGREGATE_TYPE = Homogeneous Collection (If Possible)
    MODE = Geometry - Assemble One Level
    SEP = ,
    AGGREGATE -> XLinkUpdater
XLinkUpdater
    cp_schema_name = $(citydb_schema)
    -> AttributeCreator_56

Bookmark: 3D bounding boxes
AttributeCreator_56
    ATTR_TABLE = SET_TO os_type (varchar(200)) = $(FME_OS)
    -> AttributeFilter_13
AttributeFilter_13
    ATTR_NAME = os_type
    ATTR_VALUES = <Empty>,<Missing>,<Null>,<Unfiltered>,Windows,Linux,macOS
    Windows -> AttributeCreator_49
    Linux -> AttributeCreator_49
    macOS -> AttributeCreator_58
AttributeCreator_49
    ATTR_TABLE:
      SET_TO sql_statement (varchar(1000)) = SELECT $(citydb_schema).env_ng3_library(id, 1) FROM $(citydb_schema).ng3_library;
        SELECT $(citydb_schema).env_building(id, 1) FROM $(citydb_schema).building;
        SELECT $(citydb_schema).env_cityobjectgroup(id, 1) FROM $(citydb_schema).ng3_urban_function_area;
        SELECT $(citydb_schema).env_cityobject(co.id, 1) FROM $(citydb_schema).cityobject AS co JOIN $(citydb_schema).objectclass AS o ON (co.objectclass_id = o.id AND o.classname = 'WeatherStation');
        SELECT 1 AS result;
    -> SQLExecutor_9 [INITIATOR]
Note: Compute/update 3D bounding boxes of all inserted data
SQLExecutor_9
    COMBINE_ATTRS = Result Attributes Only
    COMBINE_GEOM = Initiator Geometry Only
    DATASET = Shared 3DCityDB connection
    EXPOSED_ATTRIBUTE_LIST = result
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    POSTGRES_SCHEMAS_FOR_TABLE_LISTING = $(citydb_schema)
    SQL_STATEMENT = @Value(sql_statement)
    RESULT -> Aggregator_4
    INITIATOR -> Aggregator_3
AttributeCreator_58
    ATTR_TABLE:
      SET_TO sql_statement (varchar(1000)) = SELECT $(citydb_schema).env_ng3_library(id, 1) FROM $(citydb_schema).ng3_library;
        SELECT $(citydb_schema).env_building(id, 1) FROM $(citydb_schema).building;
        SELECT $(citydb_schema).env_cityobjectgroup(id, 1) FROM $(citydb_schema).ng3_urban_function_area;
        SELECT $(citydb_schema).env_cityobject(co.id, 1) FROM $(citydb_schema).cityobject AS co JOIN $(citydb_schema).objectclass AS o ON (co.objectclass_id = o.id AND o.classname = 'WeatherStation');
        SELECT 1 AS result;
      SET_TO warning (varchar(1000)) = WARNING - READ ME

        As you are running FME on a macOS machine, you will have to update the bounding box values of the new ADE objects manually, as there seems to be a bug in the FME SQL Executor with macOS.
        Please refer to the Energy ADE Specifications, section 7.6.2 for more details.

        Alternatively, simply run the following SQL statement in a SQL console (e.g. PgAdmin) upon conclusion of the FME run.

        ------------
        SELECT $(citydb_schema).env_ng3_library(id, 1) FROM $(citydb_schema).ng3_library;
        SELECT $(citydb_schema).env_building(id, 1) FROM $(citydb_schema).building;
        SELECT $(citydb_schema).env_cityobjectgroup(id, 1) FROM $(citydb_schema).ng3_urban_function_area;
        SELECT $(citydb_schema).env_cityobject(co.id, 1) FROM $(citydb_schema).cityobject AS co JOIN $(citydb_schema).objectclass AS o ON (co.objectclass_id = o.id AND o.classname = 'WeatherStation');
        -----------
    -> SQLExecutor_13 [INITIATOR]
    -> AttributeKeeper_24
Note: Compute/update 3D bounding boxes of all inserted data
SQLExecutor_13
    COMBINE_ATTRS = Result Attributes Only
    COMBINE_GEOM = Initiator Geometry Only
    DATASET = Shared 3DCityDB connection
    EXPOSED_ATTRIBUTE_LIST = result
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    POSTGRES_SCHEMAS_FOR_TABLE_LISTING = $(citydb_schema)
    SQL_STATEMENT = @Value(sql_statement)
    RESULT -> Aggregator_4
    INITIATOR -> Aggregator_3
Aggregator_4
    ACCUM_ATTRS_NAME = Drop Incoming Attributes
    MODE = Attributes Only
    SEP = ,
    AGGREGATE -> Aggregator_5
Aggregator_3
    ACCUM_ATTRS_NAME = Drop Incoming Attributes
    MODE = Attributes Only
    SEP = ,
    AGGREGATE -> Aggregator_5
Aggregator_5
    ACCUM_ATTRS_NAME = Drop Incoming Attributes
    AGGREGATE_TYPE = Homogeneous Collection (If Possible)
    MODE = Geometry - Assemble One Level
    SEP = ,
    AGGREGATE -> AttributeCreator_42
AttributeKeeper_24
    CREATE_BULK_MODE_FEATURES = NO
    KEEP_ATTRS = warning
    -> Logger
Logger
    LOG_FEATURE = NONE
    MAXFEATS = 1
    MESSAGE = @Value(warning)
    SEVERITY = WARN
    LOGGED -> AttributeFilter_13_macOS
Note: WARNING to macOS users
AttributeFilter_13_macOS: Inspector

Bookmark: End of the process
Note: Final message to the user
AttributeCreator_42
    ATTR_TABLE = SET_TO message (varchar(114)) = SUCCESS! Enjoy the Energy ADE 3.0! But don't forget: Adding pineapple to a pizza is a still gastronomic crime!
    -> AttributeCreator_42_Output
AttributeCreator_42_Output: Inspector

FME custom transformer ADE_Feature_editor

Parameters:
- CITYGML_FEATURE_ROLE = @Value(citygml_feature_role)   # Citygml Feature Role
- CITYGML_FEATURE_ROLE_ATTR_NAME = @Value(citygml_feature_role_attr_name)   # Citygml Feature Role Attr Name
- CITYGML_FEATURE_ROLE_ATTR_VAL = @Value(citygml_feature_role_attr_val)   # Citygml Feature Role Attr Val
- CITYGML_TARGET_URI = @Value(citygml_target_uri)   # Citygml Target Uri
- GML_DESCRIPTION = @Value(gml_description)   # Gml Description
- GML_ID = @Value(gml_id)   # Gml Id
- GML_NAME = @Value(gml_name)   # Gml Name
- GML_PARENT_ID = @Value(gml_parent_id)   # Gml Parent Id
- OBJECTCLASS_NAME = @Value(objectclass_name)   # Objectclass Name
- OBJECTCLASS_ID = @Value(objectclass_id)   # Objectclass Id

ADE_Feature (input)
    -> AttributeManager
objectclass_name_list (input)
    -> AttributeKeeper
ADE_Feature (output)

Bookmark: New Bookmark
Note: Rename ADE Feature attributes to be written in CITYOBJECT table
AttributeManager
    ATTR_TABLE:
      RENAME_SET_VALUE gml_id > gmlid (buffer)
      REMOVE citygml_target_uri (buffer)
      REMOVE citygml_feature_role (buffer)
      REMOVE citygml_feature_role_attr_name (buffer)
      REMOVE citygml_feature_role_attr_val (buffer)
      RENAME_SET_VALUE gml_description > description (buffer)
      RENAME_SET_VALUE gml_name > name (buffer)
    -> BulkAttributeRenamer_58
Note: Remove nrg3_ prefix from attributes
BulkAttributeRenamer_58
    ATTRCHOICE_ACTION = NONPROTECTEDFME
    CASE_DISP = NO
    MODE_CHOICE = RENAME
    PATTERN_ACTION_DISP = STRINGREPLACE
    REPLACE_PATTERN = nrg3_
    ATTRCHOICE = All Attributes
    -> BulkAttributeRenamer_59
BulkAttributeRenamer_59
    ATTRCHOICE_ACTION = NONPROTECTEDFME
    CASE_DISP = NO
    MODE_CHOICE = RENAME
    PATTERN_ACTION_DISP = STRINGREPLACE
    REPLACE_PATTERN = _units
    REPLACE_STR = _uom
    ATTRCHOICE = All Attributes
    -> AttributeExposer_3
Note: Expose fme_feature_type attribute
AttributeExposer_3
    ATTR_TABLE = fme_feature_type,
    -> AttributeSplitter_2
AttributeSplitter_2
    ATTR_NAME = fme_feature_type
    DELIMITER = _
    DROP_EMPTY_PARTS = NO
    LIST_NAME = _list
    TRIM_TYPE = BOTH
    -> AttributeCreator_36
AttributeCreator_36
    ATTR_TABLE:
      SET_TO objectclass_name_prefix (varchar(200)) = @Value(_list{0})
      SET_TO objectclass_name (varchar(200)) = @Value(_list{1})
    -> AttributeRemover
AttributeRemover
    LIST_ATTRS = _list{}
    REMOVE_ATTRS = objectclass_name_prefix,fme_feature_type
    -> FeatureMerger_28 [REQUESTOR]
AttributeKeeper
    CREATE_BULK_MODE_FEATURES = NO
    KEEP_ATTRS = objectclass_name,objectclass_id
    -> FeatureMerger_28 [SUPPLIER]
FeatureMerger_28
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter
Note: Sort by gmlid
Sorter
    SORT_PARM = gmlid NATURAL ASCENDING
    SORTED -> Counter_15
Note: CITYOBJECT counter: add ID unique value
Counter_15
    CNT_ATTR = id
    DOMAIN = cityobject
    SCOPE = Global
    START = 0
    -> ADE_Feature (output)

FME custom transformer CreationTerminationDate-Converter

Parameters:
- CREATION_DATE = @Value(creation_date)   # Creation Date
- TERMINATION_DATE = @Value(termination_date)   # Termination Date

Tester_5_Input (input)
    -> Tester_5
Tester_5
    BOOL_OP = OR
    TEST_CLAUSE = CASE_INSENSITIVE_TEST creation_date ATTRIBUTE_HAS_A_VALUE ""
    TEST_MODE = CASE_INSENSITIVE_TEST
    PASSED -> DateTimeConverter_6
    FAILED -> Tester_6
DateTimeConverter_6
    DATETIME_ATTR = creation_date
    IN_FORMAT = %Y-%m-%d$
    OUT_FORMAT = %Y-%m-%dT%H:%M:%S
    PASSTHROUGH = YES
    REPAIR_INPUT = YES
    -> AttributeCreator_60
AttributeCreator_60
    ATTR_TABLE = SET_TO creation_date (buffer) = @DateTimeFormat(@TimeZoneSet(@Value(creation_date),local),ISO)
    -> Tester_6
Tester_6
    BOOL_OP = OR
    TEST_CLAUSE = CASE_INSENSITIVE_TEST termination_date ATTRIBUTE_HAS_A_VALUE ""
    TEST_MODE = CASE_INSENSITIVE_TEST
    PASSED -> DateTimeConverter_4
    FAILED -> FeatureHolder_Output (output)
DateTimeConverter_4
    DATETIME_ATTR = creation_date
    IN_FORMAT = %Y-%m-%d$
    OUT_FORMAT = %Y-%m-%dT%H:%M:%S
    PASSTHROUGH = YES
    REPAIR_INPUT = YES
    -> AttributeCreator_59
AttributeCreator_59
    ATTR_TABLE = SET_TO creation_date (buffer) = @DateTimeFormat(@TimeZoneSet(@Value(creation_date),local),ISO)
    -> FeatureHolder_Output (output)
FeatureHolder_Output (output)

FME custom transformer SurfaceGeometryWriter

Parameters:
- cp_citydb_schema =
- ID = @Value(id)   # id
- _GEOMETRY_NAME = @Value(_geometry_name)   # Geometry Name

Input (input)
    -> AttributeRenamer_2
AttributeRenamer_2
    ATTR_TABLE = RENAME_SET_DEFAULT id > cityobject_id
    KEEP_RENAMED_ONLY = no
    MISSING_INPUT_ATTRS = REMOVE
    -> AppearanceRemover
AppearanceRemover
    SIDE_OPTION = BOTH
    SIDE_TO_REMOVE = Front and Back Sides
    -> GeometryFilter
    <REJECTED> -> GeometryFilter
GeometryFilter
    FILTER_MODE = SIMPLE
    FILTER_MULTI = FILTER_TYPES]"Area Surface Solid"]FME_CONTROLLER_QUERY_FILE]]FME_CONTROLLER_CHOICE]Simple
    Area -> AttributeCreator_66
    Surface -> AggregateFilter
    Solid -> AggregateFilter_2
AggregateFilter
    AGGREGATE -> AttributeCreator_65
    NOT_AGGREGATE -> AttributeCreator_66
Note: Polygon
AttributeCreator_66
    ATTR_TABLE = SET_TO classname (buffer) = Polygon
    -> SurfaceGeometryWriter:_Polygon
SurfaceGeometryWriter:_Polygon: Inspector [off]
Note: MultiSurface
AttributeCreator_65
    ATTR_TABLE = SET_TO classname (buffer) = MultiSurface
    -> Counter_44
Note: SURFACE_GEOMETRY counter
Counter_44
    CNT_ATTR = id
    DOMAIN = surface_geometry
    SCOPE = Global
    START = 0
    -> GeometryPropertyExtractor_5
Note: MultiSurface
GeometryPropertyExtractor_5
    EXTRACTTYPE = EXTRACT_TRAITS
    GQUERY:
      for $geom in //geometry
      where $geom/@fme_geometry_type = 'IFMEMultiSurface'
      return number($geom/@fme_id)
    PREFIX_EXTRACTED_TRAITS = No
    TRAIT_ATTR_LIST = gml_id,No
    EXTRACTTYPE_PARAM = Traits
    EXTRACTED -> AttributeCreator_55
    UNMATCHED -> AttributeCreator_56
AttributeCreator_56
    ATTR_TABLE = SET_TO gml_id (varchar(200)) = new_MultiSurface_UUID_@UUID()
    -> AttributeCreator_55
AttributeCreator_55
    ATTR_TABLE:
      SET_TO root_id (varchar(200)) = @Value(id)
      SET_TO parent_id (varchar(14)) = FME_NULL_VALUE
      SET_TO is_solid (uint8) = 1
    -> AttributeCreator_57
AttributeCreator_57
    ATTR_TABLE:
      SET_TO root_id (varchar(200)) = @Value(id)
      SET_TO parent_id (varchar(14)) = FME_NULL_VALUE
      SET_TO is_solid (uint8) = 0
      SET_TO is_composite (uint8) = 0
      SET_TO is_triangulated (uint8) = 0
      SET_TO is_reverse (uint8) = 0
      SET_TO is_xlink (uint8) = 0
    -> AttributeKeeper_85
    -> GeometryRemover_3
GeometryRemover_3
    REMOVE_COORDSYS = No
    -> GeometryRemover
AggregateFilter_2
    AGGREGATE -> AttributeCreator_68
    NOT_AGGREGATE -> AttributeCreator_67
Note: Solid
AttributeCreator_67
    ATTR_TABLE = SET_TO classname (buffer) = Solid
    -> Counter_43
Note: SURFACE_GEOMETRY counter
Counter_43
    CNT_ATTR = id
    DOMAIN = surface_geometry
    SCOPE = Global
    START = 0
    -> GeometryPropertyExtractor
Note: Solid
GeometryPropertyExtractor
    EXTRACTTYPE = EXTRACT_TRAITS
    GQUERY:
      for $geom in //geometry
      where $geom/@fme_geometry_type = 'IFMEBRepSolid'
      return number($geom/@fme_id)
    PREFIX_EXTRACTED_TRAITS = No
    TRAIT_ATTR_LIST = gml_id,No
    EXTRACTTYPE_PARAM = Traits
    EXTRACTED -> AttributeCreator_17
    UNMATCHED -> AttributeCreator_18
AttributeCreator_18
    ATTR_TABLE = SET_TO gml_id (varchar(200)) = new_Solid_UUID_@UUID()
    -> AttributeCreator_17
AttributeCreator_17
    ATTR_TABLE:
      SET_TO root_id (varchar(200)) = @Value(id)
      SET_TO parent_id (varchar(14)) = FME_NULL_VALUE
      SET_TO is_solid (uint8) = 1
      SET_TO is_triangulated (uint8) = 0
      SET_TO is_composite (uint8) = 0
      SET_TO is_xlink (uint8) = 0
      SET_TO is_reverse (uint8) = 0
    -> AttributeKeeper_84
    -> AttributeRenamer_137
AttributeKeeper_84
    CREATE_BULK_MODE_FEATURES = NO
    KEEP_ATTRS = cityobject_id,root_id
    -> GeometryCoercer
GeometryCoercer
    GQUERY:
      for $geom in //geometry
      where $geom/count(parent::geometry) = 0
      return number($geom/@fme_id)
    KIND = fme_composite_surface
    COERCED -> Counter_45
Note: SURFACE_GEOMETRY counter
Counter_45
    CNT_ATTR = id
    DOMAIN = surface_geometry
    SCOPE = Global
    START = 0
    -> GeometryPropertyExtractor_2
Note: CompositeSurface
GeometryPropertyExtractor_2
    EXTRACTTYPE = EXTRACT_TRAITS
    GQUERY:
      for $geom in //geometry
      where $geom/@fme_geometry_type = 'IFMECompositeSurface'
      return number($geom/@fme_id)
    PREFIX_EXTRACTED_TRAITS = No
    TRAIT_ATTR_LIST = gml_id,No
    EXTRACTTYPE_PARAM = Traits
    EXTRACTED -> AttributeCreator_15
    UNMATCHED -> AttributeCreator_26
AttributeCreator_26
    ATTR_TABLE = SET_TO gml_id (varchar(200)) = new_CompositeSurface_UUID_@UUID()
    -> AttributeCreator_15
AttributeCreator_15
    ATTR_TABLE:
      SET_TO parent_id (varchar(14)) = @Value(root_id)
      SET_TO is_solid (uint8) = 0
      SET_TO is_composite (uint8) = 1
      SET_TO is_triangulated (uint8) = 0
      SET_TO is_xlink (uint8) = 0
      SET_TO is_reverse (uint8) = 0
      SET_TO classname (varchar(16)) = CompositeSurface
    -> GeometryRemover
    -> AttributeKeeper_85
GeometryRemover
    REMOVE_COORDSYS = No
    -> AttributeRenamer_137
AttributeKeeper_85
    CREATE_BULK_MODE_FEATURES = NO
    KEEP_ATTRS = cityobject_id,root_id,id
    -> AttributeRenamer_113
AttributeRenamer_113
    ATTR_TABLE = RENAME_SET_DEFAULT id > parent_id
    KEEP_RENAMED_ONLY = no
    MISSING_INPUT_ATTRS = REMOVE
    -> Deaggregator_9
Deaggregator_9
    ATTR_ACCUM_MODE = Merge List Attributes
    ATTR_CONFLICT_RES_LOOKUP = INCOMING_IF_CONFLICT
    EXPLODE_INSTANCES = No
    LIST_ATTR_MODE_LOOKUP = LEAN
    RECURSIVE = No
    SPLIT_COMPOSITES = Yes
    ATTR_CONFLICT_RES = Use List Attribute Values
    MODE = Flatten One Level
    DEAGGREGATED -> Counter_46
Note: SURFACE_GEOMETRY counter
Counter_46
    CNT_ATTR = id
    DOMAIN = surface_geometry
    SCOPE = Global
    START = 0
    -> GeometryPropertyExtractor_3
Note: Polygon (Face): gml_id
GeometryPropertyExtractor_3
    EXTRACTTYPE = EXTRACT_TRAITS
    GQUERY:
      for $geom in //geometry
      where $geom/@fme_geometry_type = 'IFMEFace'
      return number($geom/@fme_id)
    PREFIX_EXTRACTED_TRAITS = No
    TRAIT_ATTR_LIST = gml_id,No
    EXTRACTTYPE_PARAM = Traits
    EXTRACTED -> GeometryPropertyExtractor_4
    UNTOUCHED -> AttributeCreator_53
AttributeCreator_53
    ATTR_TABLE = SET_TO gml_id (varchar(200)) = new_Polygon_UUID_@UUID()
    -> GeometryPropertyExtractor_4
Note: Polygon (Face): XLink
GeometryPropertyExtractor_4
    EXTRACTTYPE = EXTRACT_TRAITS
    GQUERY:
      for $geom in //geometry
      where $geom/@fme_geometry_type = 'IFMEFace'
      return number($geom/@fme_id)
    PREFIX_EXTRACTED_TRAITS = No
    TRAIT_ATTR_LIST = xlink_href,No
    EXTRACTTYPE_PARAM = Traits
    EXTRACTED -> AttributeCreator_40
    UNTOUCHED -> AttributeCreator_54
AttributeCreator_40
    ATTR_TABLE = SET_TO is_xlink (uint8) = 2
    -> GeometryPropertyExtractor_6
AttributeCreator_54
    ATTR_TABLE = SET_TO is_xlink (varchar(14)) = 0
    -> GeometryPropertyExtractor_6
Note: Polygon (Face): Orientation
GeometryPropertyExtractor_6
    EXTRACTTYPE = EXTRACT_TRAITS
    GQUERY:
      for $geom in //geometry
      where $geom/@fme_geometry_type = 'IFMEFace'
      return number($geom/@fme_id)
    PREFIX_EXTRACTED_TRAITS = No
    TRAIT_ATTR_LIST = gml_orientation,No
    EXTRACTTYPE_PARAM = Traits
    EXTRACTED -> AttributeFilter_22
    UNTOUCHED -> AttributeCreator_63
AttributeFilter_22
    ATTR_NAME = gml_orientation
    ATTR_VALUES = <Empty>,<Missing>,<Null>,<Unfiltered>,-
    <UNFILTERED> -> AttributeCreator_63
    - -> AttributeCreator_62
AttributeCreator_62
    ATTR_TABLE = SET_TO is_reverse (uint8) = 1
    -> AttributeCreator_64
AttributeCreator_63
    ATTR_TABLE = SET_TO is_reverse (uint8) = 0
    -> AttributeCreator_64
AttributeCreator_64
    ATTR_TABLE:
      SET_TO is_solid (uint8) = 0
      SET_TO is_triangulated (uint8) = 0
      SET_TO is_composite (uint8) = 0
      SET_TO classname (varchar(7)) = Polygon
    -> GeometryCoercer_2
Note: Corce Faces to Polygons for PostGIS
GeometryCoercer_2
    GQUERY:
      for $geom in //geometry
      where $geom/count(parent::geometry) = 0
      return number($geom/@fme_id)
    KIND = fme_polygon
    COERCED -> AttributeRenamer_137
AttributeRenamer_137
    ATTR_TABLE = RENAME_SET_DEFAULT gml_id > gmlid
    KEEP_RENAMED_ONLY = no
    MISSING_INPUT_ATTRS = REMOVE
    -> AttributeKeeper_92
AttributeKeeper_92
    CREATE_BULK_MODE_FEATURES = NO
    KEEP_ATTRS = cityobject_id,gmlid,id,is_composite,is_reverse,is_solid,is_triangulated,is_xlink,parent_id,root_id,classname,_geometry_name
    -> Sorter_36
    -> AttributeFilter_2
Sorter_36 [off]
    SORT_PARM = cityobject_id NUMERIC ASCENDING root_id NUMERIC ASCENDING parent_id NUMERIC ASCENDING gmlid NATURAL ASCENDING
    SORTED -> AttributeFilter
AttributeFilter_2
    ATTR_NAME = classname
    ATTR_VALUES = <Empty>,<Missing>,<Null>,<Unfiltered>,Solid,CompositeSurface,MultiSurface,Polygon
    Solid -> Sorter_2
    CompositeSurface -> Sorter_2
    MultiSurface -> Sorter_2
    Polygon -> Sorter_3
Sorter_2
    SORT_PARM = cityobject_id NUMERIC ASCENDING root_id NUMERIC ASCENDING parent_id NUMERIC ASCENDING gmlid NATURAL ASCENDING
    SORTED -> FeatureWriter_2 [citydb.surface_geometry]
Note: Write: / root Solids / geometrly less CompositeSurfaces / root and geometryless MultiSurfaces
FeatureWriter_2
    DATASET = Shared 3DCityDB connection
    DATASET_ATTR = _dataset
    FEATURE_TYPE_LIST_ATTR = _feature_types
    FORMAT = POSTGIS
    POSTGIS_BULK_COPY = YES
    POSTGIS_COORDINATE_SYSTEM_GRANULARITY = FEATURE
    POSTGIS_GENERIC_GEOMETRY = yes
    POSTGIS_LOWERCASE_ATTRIBUTE_NAMES = Yes
    POSTGIS_NAMED_CONNECTION = 3DCityDB connection
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
    citydb.surface_geometry -> GeometryRemover_2
    SUMMARY -> AttributeKeeper_2
GeometryRemover_2
    REMOVE_COORDSYS = No
    -> AttributeFilter
AttributeFilter
    ATTR_NAME = classname
    ATTR_VALUES = <Empty>,<Missing>,<Null>,<Unfiltered>,MultiSurface,Solid
    MultiSurface -> AttributeRenamer
    MultiSurface -> AttributeRenamer_3
    Solid -> AttributeRenamer
    Solid -> AttributeRenamer_3
AttributeRenamer
    ATTR_TABLE:
      RENAME_SET_DEFAULT id > sg_id
      RENAME_SET_DEFAULT cityobject_id > id
      RENAME_SET_DEFAULT gmlid > sg_gml_id
    KEEP_RENAMED_ONLY = no
    MISSING_INPUT_ATTRS = REMOVE
    -> AttributeKeeper_3
AttributeKeeper_3
    CREATE_BULK_MODE_FEATURES = NO
    KEEP_ATTRS = id,sg_id
    -> sg_ids (output)
sg_ids (output)
AttributeRenamer_3
    ATTR_TABLE:
      RENAME_SET_DEFAULT id > sg_id
      RENAME_SET_DEFAULT gmlid > gml_link
    KEEP_RENAMED_ONLY = no
    MISSING_INPUT_ATTRS = REMOVE
    -> AttributeKeeper_4
AttributeKeeper_4
    CREATE_BULK_MODE_FEATURES = NO
    KEEP_ATTRS = sg_id,cityobject_id,gml_link
    -> sg_gml_ids (output)
sg_gml_ids (output)
AttributeKeeper_2
    CREATE_BULK_MODE_FEATURES = NO
    -> FeatureMerger [SUPPLIER]
Sorter_3
    SORT_PARM = cityobject_id NUMERIC ASCENDING root_id NUMERIC ASCENDING parent_id NUMERIC ASCENDING gmlid NATURAL ASCENDING
    SORTED -> FeatureMerger [REQUESTOR]
FeatureMerger
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureWriter_3 [citydb.surface_geometry]
Note: Write Polygons
FeatureWriter_3
    DATASET = Shared 3DCityDB connection
    DATASET_ATTR = _dataset
    FEATURE_TYPE_LIST_ATTR = _feature_types
    FORMAT = POSTGIS
    POSTGIS_BULK_COPY = YES
    POSTGIS_COORDINATE_SYSTEM_GRANULARITY = FEATURE
    POSTGIS_GENERIC_GEOMETRY = yes
    POSTGIS_LOWERCASE_ATTRIBUTE_NAMES = Yes
    POSTGIS_NAMED_CONNECTION = 3DCityDB connection
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
Note: MultiSolid
AttributeCreator_68
    ATTR_TABLE = SET_TO classname (buffer) = MultiSurface
    -> SurfaceGeometryWriter:_MultiSolid
SurfaceGeometryWriter:_MultiSolid: Inspector [off]

FME custom transformer Feature_editor

Parameters:
- OBJECTCLASS_ID = @Value(objectclass_id)   # Objectclass Id
- OBJECTCLASS_NAME = @Value(objectclass_name)   # Objectclass Name
- ID = @Value(id)   # id
- GMLID = @Value(gmlid)   # gmlid
- GML_PARENT_ID = @Value(gml_parent_id)   # Gml Parent Id

Input (input)
    -> AttributeRenamer
f_objectclass_name_list (input)
    -> AttributeKeeper_2
AttributeKeeper_14 [off]
    CREATE_BULK_MODE_FEATURES = NO
    KEEP_ATTRS = id,gmlid
    -> AttributeRenamer_11
AttributeRenamer_11 [off]
    ATTR_TABLE:
      RENAME_SET_DEFAULT id > parent_id
      RENAME_SET_DEFAULT gmlid > gml_parent_id
    KEEP_RENAMED_ONLY = no
    MISSING_INPUT_ATTRS = REMOVE
    -> FeatureMerger_2 [SUPPLIER]
Note: Assign database parent ID
FeatureMerger_2 [off]
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> Sorter
Feature (output)
Feature_not_in_database (output)

Bookmark: New Bookmark
Note: Rename ADE Feature attributes to be written in CITYOBJECT table
AttributeRenamer
    ATTR_TABLE = RENAME_SET_DEFAULT gml_id > gmlid
    KEEP_RENAMED_ONLY = no
    MISSING_INPUT_ATTRS = REMOVE
    -> BulkAttributeRenamer_58
Note: Remove nrg3_ prefix from attributes
BulkAttributeRenamer_58
    ATTRCHOICE_ACTION = NONPROTECTEDFME
    CASE_DISP = NO
    MODE_CHOICE = RENAME
    PATTERN_ACTION_DISP = STRINGREPLACE
    REPLACE_PATTERN = nrg3_
    ATTRCHOICE = All Attributes
    -> BulkAttributeRenamer_59
BulkAttributeRenamer_59
    ATTRCHOICE_ACTION = NONPROTECTEDFME
    CASE_DISP = NO
    MODE_CHOICE = RENAME
    PATTERN_ACTION_DISP = STRINGREPLACE
    REPLACE_PATTERN = _units
    REPLACE_STR = _uom
    ATTRCHOICE = All Attributes
    -> AttributeExposer_3
Note: Expose fme_feature_type attribute
AttributeExposer_3
    ATTR_TABLE = fme_feature_type,
    -> AttributeSplitter_2
AttributeSplitter_2
    ATTR_NAME = fme_feature_type
    DELIMITER = _
    DROP_EMPTY_PARTS = NO
    LIST_NAME = _list
    TRIM_TYPE = BOTH
    -> AttributeCreator_36
AttributeCreator_36
    ATTR_TABLE:
      SET_TO objectclass_name_prefix (varchar(200)) = @Value(_list{0})
      SET_TO objectclass_name (varchar(200)) = @Value(_list{1})
    -> AttributeRemover
AttributeRemover
    LIST_ATTRS = _list{}
    REMOVE_ATTRS = objectclass_name_prefix,fme_feature_type
    -> FeatureMerger_28 [REQUESTOR]
AttributeKeeper_2
    CREATE_BULK_MODE_FEATURES = NO
    KEEP_ATTRS = objectclass_id,objectclass_name,id,gmlid
    -> FeatureMerger_28 [SUPPLIER]
    -> AttributeKeeper_14
Note: Assign database ID
FeatureMerger_28
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> FeatureMerger_2 [REQUESTOR]
    MERGED -> Sorter
    UNMERGED_REQUESTOR -> Feature_not_in_database (output)
Note: Sort by gmlid
Sorter
    SORT_PARM = gmlid NATURAL ASCENDING
    SORTED -> Feature (output)

FME custom transformer ADE_CityObject_editor

Parameters:
- CITYGML_CREATIONDATE = @Value(citygml_creationDate)   # Citygml Creationdate
- CITYGML_FEATURE_ROLE = @Value(citygml_feature_role)   # Citygml Feature Role
- CITYGML_FEATURE_ROLE_ATTR_NAME = @Value(citygml_feature_role_attr_name)   # Citygml Feature Role Attr Name
- CITYGML_FEATURE_ROLE_ATTR_VAL = @Value(citygml_feature_role_attr_val)   # Citygml Feature Role Attr Val
- CITYGML_RELATIVE_TO_TERRAIN = @Value(citygml_relative_to_terrain)   # Citygml Relative To Terrain
- CITYGML_RELATIVE_TO_WATER = @Value(citygml_relative_to_water)   # Citygml Relative To Water
- CITYGML_TARGET_URI = @Value(citygml_target_uri)   # Citygml Target Uri
- CITYGML_TERMINATIONDATE = @Value(citygml_terminationDate)   # Citygml Terminationdate
- GML_DESCRIPTION = @Value(gml_description)   # Gml Description
- GML_ID = @Value(gml_id)   # Gml Id
- GML_NAME = @Value(gml_name)   # Gml Name
- GML_PARENT_ID = @Value(gml_parent_id)   # Gml Parent Id
- OBJECTCLASS_NAME = @Value(objectclass_name)   # Objectclass Name
- OBJECTCLASS_ID = @Value(objectclass_id)   # Objectclass Id

ADE_CityObject (input)
    -> AttributeManager
Note: Rename ADE CityObject attributes to be written in CITYOBJECT table
AttributeManager
    ATTR_TABLE:
      RENAME_SET_VALUE gml_id > gmlid (buffer)
      REMOVE citygml_target_uri (buffer)
      REMOVE citygml_feature_role_attr_name (buffer)
      REMOVE citygml_feature_role_attr_val (buffer)
      RENAME_SET_VALUE gml_description > description (buffer)
      RENAME_SET_VALUE gml_name > name (buffer)
      RENAME_SET_VALUE citygml_creationDate > creation_date (buffer)
      RENAME_SET_VALUE citygml_terminationDate > termination_date (buffer)
      RENAME_SET_VALUE citygml_relative_to_terrain > relative_to_terrain (varchar(33))
      RENAME_SET_VALUE citygml_relative_to_water > relative_to_water (varchar(38))
    -> AttributeRemover_2
AttributeRemover_2
    LIST_ATTRS = citygml_appearance{} nrg3_device{} nrg3_library_member{} nrg3_resource{} nrg3_utility_network_connection{} nrg3_weather_data{}
    -> CreationDate-Converter_2 [Tester_5_Input]
CreationDate-Converter_2: CreationTerminationDate-Converter
    CREATION_DATE = @Value(creation_date)
    TERMINATION_DATE = @Value(termination_date)
    FeatureHolder_Output -> BulkAttributeRenamer_58
Note: Remove nrg3_ prefix from attributes
BulkAttributeRenamer_58
    ATTRCHOICE_ACTION = NONPROTECTEDFME
    CASE_DISP = NO
    MODE_CHOICE = RENAME
    PATTERN_ACTION_DISP = STRINGREPLACE
    REPLACE_PATTERN = nrg3_
    ATTRCHOICE = All Attributes
    -> BulkAttributeRenamer_59
BulkAttributeRenamer_59
    ATTRCHOICE_ACTION = NONPROTECTEDFME
    CASE_DISP = NO
    MODE_CHOICE = RENAME
    PATTERN_ACTION_DISP = STRINGREPLACE
    REPLACE_PATTERN = _units
    REPLACE_STR = _uom
    ATTRCHOICE = All Attributes
    -> AttributeExposer_2
Note: Expose fme_feature_type attribute
AttributeExposer_2
    ATTR_TABLE = fme_feature_type,
    -> AttributeSplitter_3
AttributeSplitter_3
    ATTR_NAME = fme_feature_type
    DELIMITER = _
    DROP_EMPTY_PARTS = NO
    LIST_NAME = _list
    TRIM_TYPE = BOTH
    -> AttributeCreator_36
AttributeCreator_36
    ATTR_TABLE:
      SET_TO objectclass_name_prefix (varchar(200)) = @Value(_list{0})
      SET_TO objectclass_name (varchar(200)) = @Value(_list{1})
    -> CityGMLClassRenamer [AttributeFilter_Input]
CityGMLClassRenamer
    OBJECTCLASS_NAME = @Value(objectclass_name)
    OBJECTCLASS_NAME_PREFIX = @Value(objectclass_name_prefix)
    AttributeRemover_3_Output -> FeatureMerger_9 [REQUESTOR]
objectclass_name_list (input)
    -> AttributeKeeper
AttributeKeeper
    CREATE_BULK_MODE_FEATURES = NO
    KEEP_ATTRS = objectclass_id,objectclass_name
    -> FeatureMerger_9 [SUPPLIER]
FeatureMerger_9
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter
    UNMERGED_REQUESTOR -> ADE_CityObject_without_class_name (output)
Note: Sort by gmlid
Sorter
    SORT_PARM = gmlid NATURAL ASCENDING
    SORTED -> Counter_15
Note: CITYOBJECT counter: add ID unique value
Counter_15
    CNT_ATTR = id
    DOMAIN = cityobject
    SCOPE = Global
    START = 0
    -> ADE_CityObject (output)
ADE_CityObject (output)
ADE_CityObject_without_class_name (output)

FME custom transformer XLinkUpdater

Parameters:
- cp_schema_name =

Input (input)
    -> AttributeCreator_13
AttributeCreator_13
    ATTR_TABLE = SET_TO sql_statement (varchar(200)) = SELECT id, gmlid, is_xlink FROM $(cp_schema_name).surface_geometry WHERE geometry IS NOT NULL;
    -> SQLExecutor_4 [INITIATOR]
SQLExecutor_4
    ATTR_IGNORE_NULLS = No
    COMBINE_ATTRS = Keep Result Attributes if Conflict
    COMBINE_GEOM = Initiator Geometry Only
    DATASET = Shared 3DCityDB connection
    EXPOSED_ATTRIBUTE_LIST = id,gmlid,is_xlink
    FORMAT = POSTGRES
    OUTPUT_FEATURES = DATA_ONLY
    POSTGRES_CREATE_FEATURE_TABLES_FROM_DATA = Yes
    POSTGRES_NAMED_CONNECTION = Shared 3DCityDB connection
    POSTGRES_QUERY_FEATURE_TYPES_FOR_MERGE_FILTERS = Yes
    POSTGRES_READ_TIME_WITH_TIMEZONE = Yes
    POSTGRES_SCHEMAS_FOR_TABLE_LISTING = $(cp_schema_name)
    SQL_STATEMENT = @Value(sql_statement)
    RESULT -> AttributeKeeper_2
    RESULT -> AttributeKeeper_3
    INITIATOR -> AttributeKeeper_5
Note: Nothing happens here, the database for example is empty
AttributeKeeper_5
    CREATE_BULK_MODE_FEATURES = NO
    -> Aggregator_2
AttributeKeeper_2
    CREATE_BULK_MODE_FEATURES = NO
    KEEP_ATTRS = gmlid,id,is_xlink
    -> FeatureMerger [REQUESTOR]
AttributeKeeper_3
    CREATE_BULK_MODE_FEATURES = NO
    KEEP_ATTRS = gmlid,is_xlink
    -> StatisticsCalculator_2
StatisticsCalculator_2
    ATTR_ACCUM_MODE = None
    CALCULATION_MODE = LEXICAL
    FEAT_STATS = gmlid,LEXICAL,,,,<Unused>,<Unused>,,,VALUE_COUNT,<Unused>,<Unused>,<Unused>,,;is_xlink,LEXICAL,MIN,MAX,,<Unused>,<Unused>,,,,<Unused>,<Unused>,<Unused>,,
    GROUP_BY = gmlid
    SUMMARY -> AttributeFilter_3
AttributeFilter_3
    ATTR_NAME = gmlid.value_count
    ATTR_VALUES = <Empty>,<Missing>,<Null>,<Unfiltered>,1
    <UNFILTERED> -> TestFilter_2
    1 -> AttributeCreator_7
TestFilter_2
    DEFAULT_VALUE = <UNFILTERED>
    PASSED_TEST_GROUP_OUTPUT = FIRST
    TEST_LIST:
      "BOOL_OP,AND,COMPOSITE_TEST,""""""1 AND 2"""""",TEST_CLAUSE,TEST @Value(is_xlink.min) = 0
      TEST @Value(is_xlink.max) = 0",0 0,"BOOL_OP,AND,COMPOSITE_TEST,""""""1 AND 2"""""",TEST_CLAUSE,TEST @Value(is_xlink.min) = 0
      TEST @Value(is_xlink.max) = 1",0 1,"BOOL_OP,AND,COMPOSITE_TEST,""""""1 AND 2"""""",TEST_CLAUSE,TEST @Value(is_xlink.min) = 0
      TEST @Value(is_xlink.max) = 2",0 2,"BOOL_OP,AND,COMPOSITE_TEST,""""""1 AND 2"""""",TEST_CLAUSE,TEST @Value(is_xlink.min) = 1
      TEST @Value(is_xlink.max) = 0",1 0,"BOOL_OP,AND,COMPOSITE_TEST,""""""1 AND 2"""""",TEST_CLAUSE,TEST @Value(is_xlink.min) = 1
      TEST @Value(is_xlink.max) = 1",1 1,"BOOL_OP,AND,COMPOSITE_TEST,""""""1 AND 2"""""",TEST_CLAUSE,TEST @Value(is_xlink.min) = 1
      TEST @Value(is_xlink.max) = 2",1 2,"BOOL_OP,AND,COMPOSITE_TEST,""""""1 AND 2"""""",TEST_CLAUSE,TEST @Value(is_xlink.min) = 2
      TEST @Value(is_xlink.max) = 0",2 0,"BOOL_OP,AND,COMPOSITE_TEST,""""""1 AND 2"""""",TEST_CLAUSE,TEST @Value(is_xlink.min) = 2
      TEST @Value(is_xlink.max) = 1",2 1,"BOOL_OP,AND,COMPOSITE_TEST,""""""1 AND 2"""""",TEST_CLAUSE,TEST @Value(is_xlink.min) = 2
      TEST @Value(is_xlink.max) = 2",2 2
    0 1 -> AttributeCreator_2
    0 2 -> AttributeCreator_5
    1 0 -> AttributeCreator_3
    1 1 -> AttributeCreator_10
    1 2 -> AttributeCreator_9
    2 0 -> AttributeCreator_8
    2 1 -> AttributeCreator_4
    2 2 -> AttributeCreator_6
AttributeCreator_2
    ATTR_TABLE = SET_TO is_xlink_new (number(1000,500)) = 1
    -> AttributeKeeper
AttributeCreator_5
    ATTR_TABLE = SET_TO is_xlink_new (number(1000,500)) = 2
    -> AttributeKeeper
AttributeCreator_3
    ATTR_TABLE = SET_TO is_xlink_new (number(1000,500)) = 0
    -> AttributeKeeper
AttributeCreator_10
    ATTR_TABLE = SET_TO is_xlink_new (number(1000,500)) = 1
    -> AttributeKeeper
AttributeCreator_9
    ATTR_TABLE = SET_TO is_xlink_new (number(1000,500)) = 2
    -> AttributeKeeper
AttributeCreator_8
    ATTR_TABLE = SET_TO is_xlink_new (number(1000,500)) = 0
    -> AttributeKeeper
AttributeCreator_4
    ATTR_TABLE = SET_TO is_xlink_new (number(1000,500)) = 1
    -> AttributeKeeper
AttributeCreator_6
    ATTR_TABLE = SET_TO is_xlink_new (number(1000,500)) = 2
    -> AttributeKeeper
AttributeCreator_7
    ATTR_TABLE = SET_TO is_xlink_new (number(1000,500)) = 0
    -> AttributeKeeper
AttributeKeeper
    CREATE_BULK_MODE_FEATURES = NO
    KEEP_ATTRS = gmlid,is_xlink_new
    -> FeatureMerger [SUPPLIER]
FeatureMerger
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> TestFilter
TestFilter
    DEFAULT_VALUE = <UNFILTERED>
    PASSED_TEST_GROUP_OUTPUT = FIRST
    TEST_LIST:
      "BOOL_OP,AND,COMPOSITE_TEST,""""""1 AND 2"""""",TEST_CLAUSE,TEST @Value(is_xlink) = 0
      TEST @Value(is_xlink_new) = 0",no change,"BOOL_OP,AND,COMPOSITE_TEST,""""""1 AND 2"""""",TEST_CLAUSE,TEST @Value(is_xlink) = 0
      TEST @Value(is_xlink_new) = 1",0 1,"BOOL_OP,AND,COMPOSITE_TEST,""""""1 AND 2"""""",TEST_CLAUSE,TEST @Value(is_xlink) = 0
      TEST @Value(is_xlink_new) = 2",0 2,"BOOL_OP,AND,COMPOSITE_TEST,""""""1 AND 2"""""",TEST_CLAUSE,TEST @Value(is_xlink) = 1
      TEST @Value(is_xlink_new) = 0",1 0,"BOOL_OP,AND,COMPOSITE_TEST,""""""1 AND 2"""""",TEST_CLAUSE,TEST @Value(is_xlink) = 1
      TEST @Value(is_xlink_new) = 1",no change,"BOOL_OP,AND,COMPOSITE_TEST,""""""1 AND 2"""""",TEST_CLAUSE,TEST @Value(is_xlink) = 1
      TEST @Value(is_xlink_new) = 2",1 2,"BOOL_OP,AND,COMPOSITE_TEST,""""""1 AND 2"""""",TEST_CLAUSE,TEST @Value(is_xlink) = 2
      TEST @Value(is_xlink_new) = 0",2 0,"BOOL_OP,AND,COMPOSITE_TEST,""""""1 AND 2"""""",TEST_CLAUSE,TEST @Value(is_xlink) = 2
      TEST @Value(is_xlink_new) = 1",2 1,"BOOL_OP,AND,COMPOSITE_TEST,""""""1 AND 2"""""",TEST_CLAUSE,TEST @Value(is_xlink) = 2
      TEST @Value(is_xlink_new) = 2",no change
    no change -> AttributeKeeper_6
    0 1 -> AttributeCreator
    0 2 -> AttributeCreator
    1 0 -> AttributeCreator
    1 2 -> AttributeCreator
    2 0 -> AttributeCreator
    2 1 -> AttributeCreator
AttributeKeeper_6
    CREATE_BULK_MODE_FEATURES = NO
    -> Aggregator
Aggregator
    ACCUM_ATTRS_NAME = Drop Incoming Attributes
    MODE = Attributes Only
    SEP = ,
    AGGREGATE -> Aggregator_2
AttributeCreator
    ATTR_TABLE = SET_TO is_xlink (number(1000,500)) = @Value(is_xlink_new)
    -> AttributeKeeper_4
AttributeKeeper_4
    CREATE_BULK_MODE_FEATURES = NO
    KEEP_ATTRS = id,is_xlink
    -> FeatureWriter [citydb.surface_geometry]
FeatureWriter
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.surface_geometry -> FeatureWriter___cp_schema_name_.surface_geometry
    SUMMARY -> AttributeKeeper_7
AttributeKeeper_7
    CREATE_BULK_MODE_FEATURES = NO
    -> Aggregator_2
Aggregator_2
    ACCUM_ATTRS_NAME = Drop Incoming Attributes
    MODE = Attributes Only
    SEP = ,
    AGGREGATE -> Output (output)
Output (output)
FeatureWriter___cp_schema_name_.surface_geometry: Inspector [off]

FME custom transformer CityObject_editor

Parameters:
- GML_PARENT_ID = @Value(gml_parent_id)   # Gml Parent Id
- GML_ID = @Value(gml_id)   # Gml Id
- OBJECTCLASS_ID = @Value(objectclass_id)   # Objectclass Id
- OBJECTCLASS_NAME = @Value(objectclass_name)   # Objectclass Name
- GMLID = @Value(gmlid)   # gmlid
- ID = @Value(id)   # id

CityObject (input)
    -> AttributeRenamer
co_objectclass_name_list (input)
    -> AttributeKeeper_11
CityObject (output)
CityObject_without_parent (output)
CityObject_not_in_database (output)

Bookmark: New Bookmark
AttributeRenamer
    ATTR_TABLE = RENAME_SET_DEFAULT gml_id > gmlid
    KEEP_RENAMED_ONLY = no
    MISSING_INPUT_ATTRS = REMOVE
    -> AttributeRemover_3
AttributeRemover_3
    LIST_ATTRS = nrg3_building_unit{} nrg3_device{} nrg3_energy_performance_certificate{} nrg3_refurbishment_measure{} nrg3_resource{} nrg3_usage_zone{} nrg3_weather_data{}
    -> BulkAttributeRenamer_58
Note: Remove nrg3_ prefix from attributes
BulkAttributeRenamer_58
    ATTRCHOICE_ACTION = NONPROTECTEDFME
    CASE_DISP = NO
    MODE_CHOICE = RENAME
    PATTERN_ACTION_DISP = STRINGREPLACE
    REPLACE_PATTERN = nrg3_
    ATTRCHOICE = All Attributes
    -> BulkAttributeRenamer_59
BulkAttributeRenamer_59
    ATTRCHOICE_ACTION = NONPROTECTEDFME
    CASE_DISP = NO
    MODE_CHOICE = RENAME
    PATTERN_ACTION_DISP = STRINGREPLACE
    REPLACE_PATTERN = _units
    REPLACE_STR = _uom
    ATTRCHOICE = All Attributes
    -> AttributeExposer_2
Note: Expose fme_feature_type attribute
AttributeExposer_2
    ATTR_TABLE = fme_feature_type,
    -> AttributeSplitter_3
AttributeSplitter_3
    ATTR_NAME = fme_feature_type
    DELIMITER = _
    DROP_EMPTY_PARTS = NO
    LIST_NAME = _list
    TRIM_TYPE = BOTH
    -> AttributeCreator_36
AttributeCreator_36
    ATTR_TABLE:
      SET_TO objectclass_name_prefix (varchar(200)) = @Value(_list{0})
      SET_TO objectclass_name (varchar(200)) = @Value(_list{1})
    -> CityGMLClassRenamer [AttributeFilter_Input]
CityGMLClassRenamer
    OBJECTCLASS_NAME = @Value(objectclass_name)
    OBJECTCLASS_NAME_PREFIX = @Value(objectclass_name_prefix)
    AttributeRemover_3_Output -> FeatureMerger_9 [REQUESTOR]
AttributeKeeper_11
    CREATE_BULK_MODE_FEATURES = NO
    KEEP_ATTRS = objectclass_id,objectclass_name,gmlid,id
    -> AttributeKeeper_14
    -> FeatureMerger_9 [SUPPLIER]
AttributeKeeper_14
    CREATE_BULK_MODE_FEATURES = NO
    KEEP_ATTRS = gmlid,id
    -> AttributeRenamer_11
AttributeRenamer_11
    ATTR_TABLE:
      RENAME_SET_DEFAULT id > parent_id
      RENAME_SET_DEFAULT gmlid > gml_parent_id
    KEEP_RENAMED_ONLY = no
    MISSING_INPUT_ATTRS = REMOVE
    -> FeatureMerger_18 [SUPPLIER]
Note: Assign database ID
FeatureMerger_9
    ATTR_ACCUM_MODE = Merge Supplier
    ATTR_CONFLICT_RES_LOOKUP = REQUESTOR_IF_CONFLICT
    IGNORE_NULLS = No
    JOIN_KEYS = @Value(gmlid) @Value(gmlid) AUTO
    MERGE_TYPE = Attributes Only
    PROCESS_DUPS = NO
    REJECT_NULL_MISSING_KEYS = No
    SUPPLIERS_FIRST = No
    ATTR_CONFLICT_RES = Use Requestor
    MERGED -> FeatureMerger_18 [REQUESTOR]
    UNMERGED_REQUESTOR -> CityObject_not_in_database (output)
Note: Assign database parent ID
FeatureMerger_18
    ATTR_ACCUM_MODE = Merge Supplier
    ATTR_CONFLICT_RES_LOOKUP = REQUESTOR_IF_CONFLICT
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    ATTR_CONFLICT_RES = Use Requestor
    MERGED -> CityObject (output)
    UNMERGED_REQUESTOR -> AttributeCreator
AttributeCreator
    ATTR_TABLE = SET_TO parent_id (varchar(14)) = FME_NULL_VALUE
    -> CityObject_without_parent (output)

FME custom transformer CityGMLClassRenamer

Parameters:
- OBJECTCLASS_NAME = @Value(objectclass_name)   # Objectclass Name
- OBJECTCLASS_NAME_PREFIX = @Value(objectclass_name_prefix)   # Objectclass Name Prefix

AttributeFilter_Input (input)
    -> AttributeFilter
AttributeFilter
    ATTR_NAME = objectclass_name_prefix
    ATTR_VALUES = <Empty>,<Missing>,<Null>,<Unfiltered>,bldg,tun,brig
    <UNFILTERED> -> AttributeRemover_3
    bldg -> AttributeCreator_2
    tun -> AttributeCreator_3
    brig -> AttributeCreator_4
Note: Building
AttributeCreator_2
    ATTR_TABLE = SET_TO objectclass_name_prefix2 (varchar(8)) = Building
    -> AttributeFilter_2
AttributeFilter_2
    ATTR_NAME = objectclass_name
    ATTR_VALUES = <Empty>,<Missing>,<Null>,<Unfiltered>,BuildingFurniture,BuildingInstallation,IntBuildingInstallation,Window,Door,GroundSurface,RoofSurface,WallSurface,ClosureSurface,CeilingSurface,InteriorWallSurface,FloorSurface,OuterCeilingSurface,OuterFloorSurface,Room
    <UNFILTERED> -> Junction
    BuildingFurniture -> Junction
    BuildingInstallation -> Junction
    IntBuildingInstallation -> Junction
    Window -> AttributeCreator_5
    Door -> AttributeCreator_5
    GroundSurface -> AttributeCreator_5
    RoofSurface -> AttributeCreator_5
    WallSurface -> AttributeCreator_5
    ClosureSurface -> AttributeCreator_5
    CeilingSurface -> AttributeCreator_5
    InteriorWallSurface -> AttributeCreator_8
    FloorSurface -> AttributeCreator_5
    OuterCeilingSurface -> AttributeCreator_7
    OuterFloorSurface -> AttributeCreator_6
    Room -> AttributeCreator_5
Note: Add Building...
AttributeCreator_5
    ATTR_TABLE = SET_TO objectclass_name (varchar(8)) = @Value(objectclass_name_prefix2)@Value(objectclass_name)
    -> Junction
AttributeCreator_8
    ATTR_TABLE = SET_TO objectclass_name (varchar(27)) = InteriorBuildingWallSurface
    -> Junction
AttributeCreator_7
    ATTR_TABLE = SET_TO objectclass_name (varchar(27)) = OuterBuildingCeilingSurface
    -> Junction
AttributeCreator_6
    ATTR_TABLE = SET_TO objectclass_name (varchar(25)) = OuterBuildingFloorSurface
    -> Junction
Junction
    -> AttributeRemover_3
Note: Tunnel
AttributeCreator_3
    ATTR_TABLE = SET_TO objectclass_name_prefix2 (varchar(8)) = Tunnel
    -> AttributeFilter_3
AttributeFilter_3
    ATTR_NAME = objectclass_name
    ATTR_VALUES = <Empty>,<Missing>,<Null>,<Unfiltered>,TunnelFurniture,TunnelInstallation,IntTunnelInstallation,HollowSpace,Window,Door,GroundSurface,RoofSurface,WallSurface,ClosureSurface,CeilingSurface,InteriorWallSurface,FloorSurface,OuterCeilingSurface,OuterFloorSurface
    <UNFILTERED> -> Junction_2
    TunnelFurniture -> Junction_2
    TunnelInstallation -> Junction_2
    IntTunnelInstallation -> Junction_2
    HollowSpace -> Junction_2
    Window -> AttributeCreator_9
    Door -> AttributeCreator_9
    GroundSurface -> AttributeCreator_9
    RoofSurface -> AttributeCreator_9
    WallSurface -> AttributeCreator_9
    ClosureSurface -> AttributeCreator_9
    CeilingSurface -> AttributeCreator_9
    InteriorWallSurface -> AttributeCreator_12
    FloorSurface -> AttributeCreator_9
    OuterCeilingSurface -> AttributeCreator_10
    OuterFloorSurface -> AttributeCreator_11
Note: Add Tunnel...
AttributeCreator_9
    ATTR_TABLE = SET_TO objectclass_name (varchar(8)) = @Value(objectclass_name_prefix2)@Value(objectclass_name)
    -> Junction_2
AttributeCreator_12
    ATTR_TABLE = SET_TO objectclass_name (varchar(27)) = InteriorTunnelWallSurface
    -> Junction_2
AttributeCreator_10
    ATTR_TABLE = SET_TO objectclass_name (varchar(25)) = OuterTunnelCeilingSurface
    -> Junction_2
AttributeCreator_11
    ATTR_TABLE = SET_TO objectclass_name (varchar(27)) = OuterTunnelCeilingSurface
    -> Junction_2
Junction_2
    -> AttributeRemover_3
Note: Bridge
AttributeCreator_4
    ATTR_TABLE = SET_TO objectclass_name_prefix2 (varchar(8)) = Bridge
    -> AttributeFilter_4
AttributeFilter_4
    ATTR_NAME = objectclass_name
    ATTR_VALUES = <Empty>,<Missing>,<Null>,<Unfiltered>,BridgeFurniture,BridgeInstallation,IntBridgeInstallation,BridgeConstructionElement,Room,Window,Door,GroundSurface,RoofSurface,WallSurface,ClosureSurface,CeilingSurface,InteriorWallSurface,FloorSurface,OuterCeilingSurface,OuterFloorSurface
    <UNFILTERED> -> Junction_3
    Room -> AttributeCreator_13
    Window -> AttributeCreator_13
    Door -> AttributeCreator_13
    GroundSurface -> AttributeCreator_13
    RoofSurface -> AttributeCreator_13
    WallSurface -> AttributeCreator_13
    ClosureSurface -> AttributeCreator_13
    CeilingSurface -> AttributeCreator_13
    InteriorWallSurface -> AttributeCreator_16
    FloorSurface -> AttributeCreator_13
    OuterCeilingSurface -> AttributeCreator_15
    OuterFloorSurface -> AttributeCreator_14
Note: Add Bridge...
AttributeCreator_13
    ATTR_TABLE = SET_TO objectclass_name (varchar(8)) = @Value(objectclass_name_prefix2)@Value(objectclass_name)
    -> Junction_3
AttributeCreator_16
    ATTR_TABLE = SET_TO objectclass_name (varchar(27)) = InteriorBridgeWallSurface
    -> Junction_3
AttributeCreator_15
    ATTR_TABLE = SET_TO objectclass_name (varchar(27)) = OuterBridgeCeilingSurface
    -> Junction_3
AttributeCreator_14
    ATTR_TABLE = SET_TO objectclass_name (varchar(25)) = OuterBridgeFloorSurface
    -> Junction_3
Junction_3
    -> AttributeRemover_3
AttributeRemover_3
    LIST_ATTRS = _list{}
    REMOVE_ATTRS = objectclass_name_prefix,fme_feature_type,objectclass_name_prefix2
    -> AttributeRemover_3_Output (output)
AttributeRemover_3_Output (output)

FME custom transformer QualifiedAttributeWriter

Parameters:
- cp_citydb_schema =
- TABLE_NAME = @Value(table_name)   # Table Name
- OBJECTCLASS_NAME = @Value(objectclass_name)   # Objectclass Name
- OBJECTCLASS_ID = @Value(objectclass_id)   # Objectclass Id
- TABLE_NAME_2 = @Value(table_name)   # Table Name
- ID = @Value(id)   # id

CityObject (input)
    -> AttributeFilter
objectclass_name_list (input)
    -> AttributeKeeper
Output (output)

Bookmark: QUALIFIED ATTRIBUTES
AttributeFilter
    ATTR_NAME = objectclass_name
    ATTR_VALUES = <Empty>,<Missing>,<Null>,<Unfiltered>,BuildingPart,Building,ThermalZone,UsageZone,BuildingUnit
    BuildingPart -> AttributeKeeper_48
    Building -> AttributeKeeper_48
    ThermalZone -> AttributeKeeper_49
    UsageZone -> AttributeKeeper_49
    BuildingUnit -> AttributeKeeper_49
AttributeKeeper_48
    CREATE_BULK_MODE_FEATURES = NO
    KEEP_ATTRS = id
    KEEP_LIST = area{} height{} volume{}
    -> AttributeRenamer_4
AttributeRenamer_4
    ATTR_TABLE = RENAME_SET_DEFAULT id > building_id
    KEEP_RENAMED_ONLY = no
    MISSING_INPUT_ATTRS = REMOVE
    -> AttributeKeeper_7
    -> AttributeKeeper_6
    -> AttributeKeeper_4
Note: Height
AttributeKeeper_6
    CREATE_BULK_MODE_FEATURES = NO
    KEEP_ATTRS = building_id
    KEEP_LIST = height{}
    -> ListExploder_2
ListExploder_2
    ATTR_ACCUM_MODE = Merge List Attributes
    ATTR_CONFLICT_RES_LOOKUP = INCOMING_IF_CONFLICT
    LIST_ATTR = height{}
    ATTR_CONFLICT_RES = Use List Attribute Values
    ELEMENTS -> BulkAttributeRenamer_3
BulkAttributeRenamer_3
    ATTRCHOICE_ACTION = NONPROTECTEDFME
    CASE_DISP = YES
    MODE_CHOICE = RENAME
    PATTERN_ACTION_DISP = STRINGREPLACE
    REPLACE_PATTERN = qualified_height_
    ATTRCHOICE = All Attributes
    -> AttributeCreator_5
AttributeCreator_5
    ATTR_TABLE = SET_TO objectclass_name (varchar(15)) = QualifiedHeight
    -> AttributeRenamer_2
AttributeKeeper_49
    CREATE_BULK_MODE_FEATURES = NO
    KEEP_ATTRS = id
    KEEP_LIST = area{} volume{}
    -> AttributeRenamer_93
AttributeRenamer_93
    ATTR_TABLE = RENAME_SET_DEFAULT id > building_partition_id
    KEEP_RENAMED_ONLY = no
    MISSING_INPUT_ATTRS = REMOVE
    -> AttributeKeeper_4
    -> AttributeKeeper_7
Note: Area
AttributeKeeper_4
    CREATE_BULK_MODE_FEATURES = NO
    KEEP_ATTRS = building_id,building_partition_id
    KEEP_LIST = area{}
    -> ListExploder
ListExploder
    ATTR_ACCUM_MODE = Merge List Attributes
    ATTR_CONFLICT_RES_LOOKUP = INCOMING_IF_CONFLICT
    LIST_ATTR = area{}
    ATTR_CONFLICT_RES = Use List Attribute Values
    ELEMENTS -> BulkAttributeRenamer_2
BulkAttributeRenamer_2
    ATTRCHOICE_ACTION = NONPROTECTEDFME
    CASE_DISP = YES
    MODE_CHOICE = RENAME
    PATTERN_ACTION_DISP = STRINGREPLACE
    REPLACE_PATTERN = qualified_area_
    ATTRCHOICE = All Attributes
    -> AttributeCreator_6
AttributeCreator_6
    ATTR_TABLE = SET_TO objectclass_name (varchar(15)) = QualifiedArea
    -> AttributeRenamer_2
Note: Volume
AttributeKeeper_7
    CREATE_BULK_MODE_FEATURES = NO
    KEEP_ATTRS = building_id,building_partition_id
    KEEP_LIST = volume{}
    -> ListExploder_3
ListExploder_3
    ATTR_ACCUM_MODE = Merge List Attributes
    ATTR_CONFLICT_RES_LOOKUP = INCOMING_IF_CONFLICT
    LIST_ATTR = volume{}
    ATTR_CONFLICT_RES = Use List Attribute Values
    ELEMENTS -> BulkAttributeRenamer_51
BulkAttributeRenamer_51
    ATTRCHOICE_ACTION = NONPROTECTEDFME
    CASE_DISP = YES
    MODE_CHOICE = RENAME
    PATTERN_ACTION_DISP = STRINGREPLACE
    REPLACE_PATTERN = qualified_volume_
    ATTRCHOICE = All Attributes
    -> AttributeCreator_7
AttributeCreator_7
    ATTR_TABLE = SET_TO objectclass_name (varchar(15)) = QualifiedVolume
    -> AttributeRenamer_2
AttributeRenamer_2
    ATTR_TABLE = RENAME_SET_DEFAULT type_codeSpace > type_codespace
    KEEP_RENAMED_ONLY = no
    MISSING_INPUT_ATTRS = REMOVE
    -> FeatureMerger_3 [REQUESTOR]
AttributeKeeper
    CREATE_BULK_MODE_FEATURES = NO
    KEEP_ATTRS = objectclass_name,objectclass_id,table_name
    -> AttributeFilter_2
AttributeFilter_2
    ATTR_NAME = objectclass_name
    ATTR_VALUES = <Empty>,<Missing>,<Null>,<Unfiltered>,QualifiedHeight,QualifiedArea,QualifiedVolume
    QualifiedHeight -> FeatureMerger_3 [SUPPLIER]
    QualifiedArea -> FeatureMerger_3 [SUPPLIER]
    QualifiedVolume -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(objectclass_name) @Value(objectclass_name) AUTO
    MERGE_TYPE = Attributes Only
    PROCESS_DUPS = NO
    REJECT_NULL_MISSING_KEYS = No
    SUPPLIERS_FIRST = No
    ATTR_CONFLICT_RES = Use Requestor
    MERGED -> Sorter
Sorter
    SORT_PARM = building_id NATURAL ASCENDING building_partition_id NATURAL ASCENDING objectclass_id NATURAL ASCENDING
    SORTED -> Counter_12
Note: Counter QUALIFIED_ATTRIBUTE
Counter_12
    CNT_ATTR = id
    DOMAIN = @Value(table_name)
    SCOPE = Global
    START = 0
    -> FeatureWriter [citydb.ng3_qualified_attribute]
FeatureWriter
    DATASET = Shared 3DCityDB connection
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = 3DCityDB connection
    POSTGRES_START_TRANSACTION = 0
    POSTGRES_STRICT_TEMPORAL_TYPE_HANDLING = Yes
    POSTGRES_TRANSACTION_INTERVAL = 1000
    TOTAL_FEATURES_WRITTEN_ATTR = _total_features_written
    citydb.ng3_qualified_attribute -> Output (output)
